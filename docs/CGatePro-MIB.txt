CGatePro-MIB DEFINITIONS ::= BEGIN

IMPORTS
   MODULE-IDENTITY, OBJECT-TYPE, snmpModules, enterprises,
   Counter32, Counter64, Integer32
       FROM SNMPv2-SMI;

stalkerMIB MODULE-IDENTITY
    LAST-UPDATED "202002290000Z"
    ORGANIZATION "AO StalkerSoft"
    CONTACT-INFO
          "       Technical Support


            E-mail: support@communigate.ru"
    DESCRIPTION
           "The MIB module for AO StalkerSoft products."
    REVISION     "202002290000Z"
    DESCRIPTION
           "Revision date"
    ::= { enterprises 5678}

-- 1.3.6.1.4.1.5678.2
communiGatePro OBJECT IDENTIFIER
    ::= { stalkerMIB 2}

-- 1.3.6.1.4.1.5678.2.1
cGateProObject OBJECT IDENTIFIER
    ::= { communiGatePro 1}

-- 1.3.6.1.4.1.5678.2.1.1
cGateProModule OBJECT IDENTIFIER
    ::= { cGateProObject 1}

-- 1.3.6.1.4.1.5678.2.1.1.1
smtp OBJECT IDENTIFIER
    ::= { cGateProModule 1}

-- 1.3.6.1.4.1.5678.2.1.1.1.1
smtpInput OBJECT IDENTIFIER
    ::= { smtp 1}

-- 1.3.6.1.4.1.5678.2.1.1.1.1.1
smtpInputActive OBJECT-TYPE
    SYNTAX  Integer32
    MAX-ACCESS  read-only
    STATUS  current
    DESCRIPTION "number of active SMTP input connections"
    ::= { smtpInput 1}

-- 1.3.6.1.4.1.5678.2.1.1.1.1.2
smtpInputTotal OBJECT-TYPE
    SYNTAX  Integer32
    MAX-ACCESS  read-only
    STATUS  current
    DESCRIPTION "total number of SMTP input channels"
    ::= { smtpInput 2}

-- 1.3.6.1.4.1.5678.2.1.1.1.1.3
smtpInputJobs OBJECT-TYPE
    SYNTAX  Counter64
    MAX-ACCESS  read-only
    STATUS  current
    DESCRIPTION "total number of SMTP input connections processed"
    ::= { smtpInput 3}

-- 1.3.6.1.4.1.5678.2.1.1.1.1.8
smtpInputTrafficIn OBJECT-TYPE
    SYNTAX  Counter64
    MAX-ACCESS  read-only
    STATUS  current
    DESCRIPTION "incoming SMTP data received"
    ::= { smtpInput 8}

-- 1.3.6.1.4.1.5678.2.1.1.1.1.9
smtpInputTrafficOut OBJECT-TYPE
    SYNTAX  Counter64
    MAX-ACCESS  read-only
    STATUS  current
    DESCRIPTION "incoming SMTP data sent"
    ::= { smtpInput 9}

-- 1.3.6.1.4.1.5678.2.1.1.1.1.10
smtpInputMessagesReceived OBJECT-TYPE
    SYNTAX  Counter64
    MAX-ACCESS  read-only
    STATUS  current
    DESCRIPTION "incoming SMTP: received messages"
    ::= { smtpInput 10}

-- 1.3.6.1.4.1.5678.2.1.1.1.1.11
smtpInputMessageBytesReceived OBJECT-TYPE
    SYNTAX  Counter64
    MAX-ACCESS  read-only
    STATUS  current
    DESCRIPTION "incoming SMTP: received message bytes"
    ::= { smtpInput 11}

-- 1.3.6.1.4.1.5678.2.1.1.1.1.12
smtpInputRecipientsAccepted OBJECT-TYPE
    SYNTAX  Counter64
    MAX-ACCESS  read-only
    STATUS  current
    DESCRIPTION "incoming SMTP: accepted RCPT TO commands"
    ::= { smtpInput 12}

-- 1.3.6.1.4.1.5678.2.1.1.1.1.13
smtpInputRecipientsRejected OBJECT-TYPE
    SYNTAX  Counter64
    MAX-ACCESS  read-only
    STATUS  current
    DESCRIPTION "incoming SMTP: rejected RCPT TO commands"
    ::= { smtpInput 13}

-- 1.3.6.1.4.1.5678.2.1.1.1.1.14
smtpInputReturnPathsRejected OBJECT-TYPE
    SYNTAX  Counter64
    MAX-ACCESS  read-only
    STATUS  current
    DESCRIPTION "incoming SMTP: rejected MAIL FROM commands"
    ::= { smtpInput 14}

-- 1.3.6.1.4.1.5678.2.1.1.1.1.15
smtpInputDataCommandsRejected OBJECT-TYPE
    SYNTAX  Counter64
    MAX-ACCESS  read-only
    STATUS  current
    DESCRIPTION "incoming SMTP: rejected DATA commands"
    ::= { smtpInput 15}

-- 1.3.6.1.4.1.5678.2.1.1.1.1.16
smtpInputMessageBodiesRejected OBJECT-TYPE
    SYNTAX  Counter64
    MAX-ACCESS  read-only
    STATUS  current
    DESCRIPTION "incoming SMTP: rejected message bodies"
    ::= { smtpInput 16}

-- 1.3.6.1.4.1.5678.2.1.1.1.1.17
smtpInputAuthenticationsAccepted OBJECT-TYPE
    SYNTAX  Counter64
    MAX-ACCESS  read-only
    STATUS  current
    DESCRIPTION "incoming SMTP: accepted AUTHentications"
    ::= { smtpInput 17}

-- 1.3.6.1.4.1.5678.2.1.1.1.1.18
smtpInputAuthenticationsRejected OBJECT-TYPE
    SYNTAX  Counter64
    MAX-ACCESS  read-only
    STATUS  current
    DESCRIPTION "incoming SMTP: rejected AUTHentications"
    ::= { smtpInput 18}

-- 1.3.6.1.4.1.5678.2.1.1.1.1.19
smtpInputMessageSubmitRejected OBJECT-TYPE
    SYNTAX  Counter64
    MAX-ACCESS  read-only
    STATUS  current
    DESCRIPTION "incoming SMTP: rejected on submit"
    ::= { smtpInput 19}

-- 1.3.6.1.4.1.5678.2.1.1.1.1.30
smtpInputRBLFailed OBJECT-TYPE
    SYNTAX  Counter64
    MAX-ACCESS  read-only
    STATUS  current
    DESCRIPTION "incoming SMTP: connections blacklisted with RBL"
    ::= { smtpInput 30}

-- 1.3.6.1.4.1.5678.2.1.1.1.1.31
smtpInputSPFFailed OBJECT-TYPE
    SYNTAX  Counter64
    MAX-ACCESS  read-only
    STATUS  current
    DESCRIPTION "incoming SMTP: SPF rejections"
    ::= { smtpInput 31}

-- 1.3.6.1.4.1.5678.2.1.1.1.1.32
smtpInputReverseFailed OBJECT-TYPE
    SYNTAX  Counter64
    MAX-ACCESS  read-only
    STATUS  current
    DESCRIPTION "incoming SMTP: reverse-connect rejections"
    ::= { smtpInput 32}

-- 1.3.6.1.4.1.5678.2.1.1.1.2
smtpOutput OBJECT IDENTIFIER
    ::= { smtp 2}

-- 1.3.6.1.4.1.5678.2.1.1.1.2.1
smtpOutputActive OBJECT-TYPE
    SYNTAX  Integer32
    MAX-ACCESS  read-only
    STATUS  current
    DESCRIPTION "number of active SMTP outgoing connections"
    ::= { smtpOutput 1}

-- 1.3.6.1.4.1.5678.2.1.1.1.2.2
smtpOutputTotal OBJECT-TYPE
    SYNTAX  Integer32
    MAX-ACCESS  read-only
    STATUS  current
    DESCRIPTION "total number of SMTP outgoing channels"
    ::= { smtpOutput 2}

-- 1.3.6.1.4.1.5678.2.1.1.1.2.3
smtpOutputJobs OBJECT-TYPE
    SYNTAX  Counter64
    MAX-ACCESS  read-only
    STATUS  current
    DESCRIPTION "total number of SMTP outgoing connections processed"
    ::= { smtpOutput 3}

-- 1.3.6.1.4.1.5678.2.1.1.1.2.4
smtpOutputActiveHosts OBJECT-TYPE
    SYNTAX  Integer32
    MAX-ACCESS  read-only
    STATUS  current
    DESCRIPTION "number of active SMTP domain queues"
    ::= { smtpOutput 4}

-- 1.3.6.1.4.1.5678.2.1.1.1.2.5
smtpOutputWaitingHosts OBJECT-TYPE
    SYNTAX  Integer32
    MAX-ACCESS  read-only
    STATUS  current
    DESCRIPTION "number of waiting SMTP domain queues"
    ::= { smtpOutput 5}

-- 1.3.6.1.4.1.5678.2.1.1.1.2.8
smtpOutputTrafficIn OBJECT-TYPE
    SYNTAX  Counter64
    MAX-ACCESS  read-only
    STATUS  current
    DESCRIPTION "outgoing SMTP data received"
    ::= { smtpOutput 8}

-- 1.3.6.1.4.1.5678.2.1.1.1.2.9
smtpOutputTrafficOut OBJECT-TYPE
    SYNTAX  Counter64
    MAX-ACCESS  read-only
    STATUS  current
    DESCRIPTION "outgoing SMTP data sent"
    ::= { smtpOutput 9}

-- 1.3.6.1.4.1.5678.2.1.1.1.2.10
smtpOutputMessagesSent OBJECT-TYPE
    SYNTAX  Counter64
    MAX-ACCESS  read-only
    STATUS  current
    DESCRIPTION "outgoing SMTP: sent messages"
    ::= { smtpOutput 10}

-- 1.3.6.1.4.1.5678.2.1.1.1.2.11
smtpOutputMessageBytesSent OBJECT-TYPE
    SYNTAX  Counter64
    MAX-ACCESS  read-only
    STATUS  current
    DESCRIPTION "outgoing SMTP: sent message bytes"
    ::= { smtpOutput 11}

-- 1.3.6.1.4.1.5678.2.1.1.1.2.12
smtpOutputRecipientsSent OBJECT-TYPE
    SYNTAX  Counter64
    MAX-ACCESS  read-only
    STATUS  current
    DESCRIPTION "outgoing SMTP: accepted RCPT TO commands"
    ::= { smtpOutput 12}

-- 1.3.6.1.4.1.5678.2.1.1.1.2.13
smtpOutputConnectionsMade OBJECT-TYPE
    SYNTAX  Counter64
    MAX-ACCESS  read-only
    STATUS  current
    DESCRIPTION "outgoing SMTP: established connections"
    ::= { smtpOutput 13}

-- 1.3.6.1.4.1.5678.2.1.1.1.2.14
smtpOutputConnectionsFailed OBJECT-TYPE
    SYNTAX  Counter64
    MAX-ACCESS  read-only
    STATUS  current
    DESCRIPTION "outgoing SMTP: failed connections"
    ::= { smtpOutput 14}

-- 1.3.6.1.4.1.5678.2.1.1.1.2.15
smtpOutputRecipientsRejected OBJECT-TYPE
    SYNTAX  Counter64
    MAX-ACCESS  read-only
    STATUS  current
    DESCRIPTION "outgoing SMTP: rejected RCPT TO commands"
    ::= { smtpOutput 15}

-- 1.3.6.1.4.1.5678.2.1.1.1.2.16
smtpOutputReturnPathsRejected OBJECT-TYPE
    SYNTAX  Counter64
    MAX-ACCESS  read-only
    STATUS  current
    DESCRIPTION "outgoing SMTP: rejected MAIL FROM commands"
    ::= { smtpOutput 16}

-- 1.3.6.1.4.1.5678.2.1.1.1.2.17
smtpOutputDataCommandsRejected OBJECT-TYPE
    SYNTAX  Counter64
    MAX-ACCESS  read-only
    STATUS  current
    DESCRIPTION "outgoing SMTP: rejected DATA commands"
    ::= { smtpOutput 17}

-- 1.3.6.1.4.1.5678.2.1.1.1.2.18
smtpOutputMessageBodiesRejected OBJECT-TYPE
    SYNTAX  Counter64
    MAX-ACCESS  read-only
    STATUS  current
    DESCRIPTION "outgoing SMTP: rejected message bodies"
    ::= { smtpOutput 18}

-- 1.3.6.1.4.1.5678.2.1.1.2
cGateProSIP OBJECT IDENTIFIER
    ::= { cGateProModule 2}

-- 1.3.6.1.4.1.5678.2.1.1.2.1
sipData OBJECT IDENTIFIER
    ::= { cGateProSIP 1}

-- 1.3.6.1.4.1.5678.2.1.1.2.1.1
sipTrafficIn OBJECT-TYPE
    SYNTAX  Counter64
    MAX-ACCESS  read-only
    STATUS  current
    DESCRIPTION "SIP data received"
    ::= { sipData 1}

-- 1.3.6.1.4.1.5678.2.1.1.2.1.2
sipPacketsIn OBJECT-TYPE
    SYNTAX  Counter64
    MAX-ACCESS  read-only
    STATUS  current
    DESCRIPTION "SIP packets received"
    ::= { sipData 2}

-- 1.3.6.1.4.1.5678.2.1.1.2.1.3
sipTrafficOut OBJECT-TYPE
    SYNTAX  Counter64
    MAX-ACCESS  read-only
    STATUS  current
    DESCRIPTION "SIP data sent"
    ::= { sipData 3}

-- 1.3.6.1.4.1.5678.2.1.1.2.1.4
sipPacketsOut OBJECT-TYPE
    SYNTAX  Counter64
    MAX-ACCESS  read-only
    STATUS  current
    DESCRIPTION "SIP packets sent"
    ::= { sipData 4}

-- 1.3.6.1.4.1.5678.2.1.1.2.1.5
sipRequestsIn OBJECT-TYPE
    SYNTAX  Counter64
    MAX-ACCESS  read-only
    STATUS  current
    DESCRIPTION "SIP requests received"
    ::= { sipData 5}

-- 1.3.6.1.4.1.5678.2.1.1.2.1.6
sipResponsesIn OBJECT-TYPE
    SYNTAX  Counter64
    MAX-ACCESS  read-only
    STATUS  current
    DESCRIPTION "SIP responses received"
    ::= { sipData 6}

-- 1.3.6.1.4.1.5678.2.1.1.2.1.7
sipRequestsOut OBJECT-TYPE
    SYNTAX  Counter64
    MAX-ACCESS  read-only
    STATUS  current
    DESCRIPTION "SIP requests sent"
    ::= { sipData 7}

-- 1.3.6.1.4.1.5678.2.1.1.2.1.8
sipResponsesOut OBJECT-TYPE
    SYNTAX  Counter64
    MAX-ACCESS  read-only
    STATUS  current
    DESCRIPTION "SIP responses sent"
    ::= { sipData 8}

-- 1.3.6.1.4.1.5678.2.1.1.2.1.9
sipClusterOut OBJECT-TYPE
    SYNTAX  Counter64
    MAX-ACCESS  read-only
    STATUS  current
    DESCRIPTION "SIP responses relayed for Cluster members"
    ::= { sipData 9}

-- 1.3.6.1.4.1.5678.2.1.1.2.1.10
sipPacketsDropped OBJECT-TYPE
    SYNTAX  Counter64
    MAX-ACCESS  read-only
    STATUS  current
    DESCRIPTION "SIP packets dropped (queue overloading)"
    ::= { sipData 10}

-- 1.3.6.1.4.1.5678.2.1.1.2.1.11
sipClusterRelayedInp OBJECT-TYPE
    SYNTAX  Counter64
    MAX-ACCESS  read-only
    STATUS  current
    DESCRIPTION "SIP requests relayed from Cluster members"
    ::= { sipData 11}

-- 1.3.6.1.4.1.5678.2.1.1.2.1.12
sipClusterRelayedOut OBJECT-TYPE
    SYNTAX  Counter64
    MAX-ACCESS  read-only
    STATUS  current
    DESCRIPTION "SIP requests relayed to Cluster members"
    ::= { sipData 12}

-- 1.3.6.1.4.1.5678.2.1.1.2.1.21
sipUDPTrafficIn OBJECT-TYPE
    SYNTAX  Counter64
    MAX-ACCESS  read-only
    STATUS  current
    DESCRIPTION "SIP UDP data received"
    ::= { sipData 21}

-- 1.3.6.1.4.1.5678.2.1.1.2.1.22
sipUDPPacketsIn OBJECT-TYPE
    SYNTAX  Counter64
    MAX-ACCESS  read-only
    STATUS  current
    DESCRIPTION "SIP UDP packets received"
    ::= { sipData 22}

-- 1.3.6.1.4.1.5678.2.1.1.2.1.23
sipUDPTrafficOut OBJECT-TYPE
    SYNTAX  Counter64
    MAX-ACCESS  read-only
    STATUS  current
    DESCRIPTION "SIP UDP data sent"
    ::= { sipData 23}

-- 1.3.6.1.4.1.5678.2.1.1.2.1.24
sipUDPPacketsOut OBJECT-TYPE
    SYNTAX  Counter64
    MAX-ACCESS  read-only
    STATUS  current
    DESCRIPTION "SIP UDP packets sent"
    ::= { sipData 24}

-- 1.3.6.1.4.1.5678.2.1.1.2.1.31
sipTCPTrafficIn OBJECT-TYPE
    SYNTAX  Counter64
    MAX-ACCESS  read-only
    STATUS  current
    DESCRIPTION "SIP TCP data received"
    ::= { sipData 31}

-- 1.3.6.1.4.1.5678.2.1.1.2.1.32
sipTCPPacketsIn OBJECT-TYPE
    SYNTAX  Counter64
    MAX-ACCESS  read-only
    STATUS  current
    DESCRIPTION "SIP TCP packets received"
    ::= { sipData 32}

-- 1.3.6.1.4.1.5678.2.1.1.2.1.33
sipTCPTrafficOut OBJECT-TYPE
    SYNTAX  Counter64
    MAX-ACCESS  read-only
    STATUS  current
    DESCRIPTION "SIP TCP data sent"
    ::= { sipData 33}

-- 1.3.6.1.4.1.5678.2.1.1.2.1.34
sipTCPPacketsOut OBJECT-TYPE
    SYNTAX  Counter64
    MAX-ACCESS  read-only
    STATUS  current
    DESCRIPTION "SIP TCP packets sent"
    ::= { sipData 34}

-- 1.3.6.1.4.1.5678.2.1.1.2.1.41
sipTCPConnectionsActive OBJECT-TYPE
    SYNTAX  Integer32
    MAX-ACCESS  read-only
    STATUS  current
    DESCRIPTION "active SIP TCP connections"
    ::= { sipData 41}

-- 1.3.6.1.4.1.5678.2.1.1.2.1.42
sipTCPConnectionsTotal OBJECT-TYPE
    SYNTAX  Counter64
    MAX-ACCESS  read-only
    STATUS  current
    DESCRIPTION "total SIP TCP connections"
    ::= { sipData 42}

-- 1.3.6.1.4.1.5678.2.1.1.2.1.43
sipTCPIncomingActive OBJECT-TYPE
    SYNTAX  Integer32
    MAX-ACCESS  read-only
    STATUS  current
    DESCRIPTION "active SIP TCP incoming connections"
    ::= { sipData 43}

-- 1.3.6.1.4.1.5678.2.1.1.2.1.44
sipTCPIncomingTotal OBJECT-TYPE
    SYNTAX  Counter64
    MAX-ACCESS  read-only
    STATUS  current
    DESCRIPTION "total SIP TCP incoming connections"
    ::= { sipData 44}

-- 1.3.6.1.4.1.5678.2.1.1.2.1.45
sipTCPSecureActive OBJECT-TYPE
    SYNTAX  Integer32
    MAX-ACCESS  read-only
    STATUS  current
    DESCRIPTION "active SIP TCP secure connections"
    ::= { sipData 45}

-- 1.3.6.1.4.1.5678.2.1.1.2.1.46
sipTCPSecureTotal OBJECT-TYPE
    SYNTAX  Counter64
    MAX-ACCESS  read-only
    STATUS  current
    DESCRIPTION "total SIP TCP secure connections"
    ::= { sipData 46}

-- 1.3.6.1.4.1.5678.2.1.1.2.1.50
sipEnqueuedPackets OBJECT-TYPE
    SYNTAX  Integer32
    MAX-ACCESS  read-only
    STATUS  current
    DESCRIPTION "SIP packets received but not processed"
    ::= { sipData 50}

-- 1.3.6.1.4.1.5678.2.1.1.2.2
sipServer OBJECT IDENTIFIER
    ::= { cGateProSIP 2}

-- 1.3.6.1.4.1.5678.2.1.1.2.2.1
sipServersActive OBJECT-TYPE
    SYNTAX  Integer32
    MAX-ACCESS  read-only
    STATUS  current
    DESCRIPTION "active SIP server transactions"
    ::= { sipServer 1}

-- 1.3.6.1.4.1.5678.2.1.1.2.2.2
sipServersTotal OBJECT-TYPE
    SYNTAX  Counter64
    MAX-ACCESS  read-only
    STATUS  current
    DESCRIPTION "total SIP server transactions processed"
    ::= { sipServer 2}

-- 1.3.6.1.4.1.5678.2.1.1.2.2.3
sipServerActiveEvents OBJECT-TYPE
    SYNTAX  Integer32
    MAX-ACCESS  read-only
    STATUS  current
    DESCRIPTION "unprocessed SIP server events"
    ::= { sipServer 3}

-- 1.3.6.1.4.1.5678.2.1.1.2.2.4
sipServerTotalEvents OBJECT-TYPE
    SYNTAX  Counter64
    MAX-ACCESS  read-only
    STATUS  current
    DESCRIPTION "total SIP server events processed"
    ::= { sipServer 4}

-- 1.3.6.1.4.1.5678.2.1.1.2.2.5
sipServerBusyThreads OBJECT-TYPE
    SYNTAX  Integer32
    MAX-ACCESS  read-only
    STATUS  current
    DESCRIPTION "busy SIP server processors"
    ::= { sipServer 5}

-- 1.3.6.1.4.1.5678.2.1.1.2.2.6
sipServerOverloads OBJECT-TYPE
    SYNTAX  Counter64
    MAX-ACCESS  read-only
    STATUS  current
    DESCRIPTION "total SIP server subsystem overloads"
    ::= { sipServer 6}

-- 1.3.6.1.4.1.5678.2.1.1.2.3
sipClient OBJECT IDENTIFIER
    ::= { cGateProSIP 3}

-- 1.3.6.1.4.1.5678.2.1.1.2.3.1
sipClientsActive OBJECT-TYPE
    SYNTAX  Integer32
    MAX-ACCESS  read-only
    STATUS  current
    DESCRIPTION "active SIP client transactions"
    ::= { sipClient 1}

-- 1.3.6.1.4.1.5678.2.1.1.2.3.2
sipClientsTotal OBJECT-TYPE
    SYNTAX  Counter64
    MAX-ACCESS  read-only
    STATUS  current
    DESCRIPTION "total SIP client transactions processed"
    ::= { sipClient 2}

-- 1.3.6.1.4.1.5678.2.1.1.2.3.3
sipClientActiveEvents OBJECT-TYPE
    SYNTAX  Integer32
    MAX-ACCESS  read-only
    STATUS  current
    DESCRIPTION "unprocessed SIP client events"
    ::= { sipClient 3}

-- 1.3.6.1.4.1.5678.2.1.1.2.3.4
sipClientTotalEvents OBJECT-TYPE
    SYNTAX  Counter64
    MAX-ACCESS  read-only
    STATUS  current
    DESCRIPTION "total SIP client events processed"
    ::= { sipClient 4}

-- 1.3.6.1.4.1.5678.2.1.1.2.3.5
sipClientBusyThreads OBJECT-TYPE
    SYNTAX  Integer32
    MAX-ACCESS  read-only
    STATUS  current
    DESCRIPTION "busy SIP client processors"
    ::= { sipClient 5}

-- 1.3.6.1.4.1.5678.2.1.1.2.3.6
sipClientOverloads OBJECT-TYPE
    SYNTAX  Counter64
    MAX-ACCESS  read-only
    STATUS  current
    DESCRIPTION "total SIP client subsystem overloads"
    ::= { sipClient 6}

-- 1.3.6.1.4.1.5678.2.1.1.2.4
sipSigner OBJECT IDENTIFIER
    ::= { cGateProSIP 4}

-- 1.3.6.1.4.1.5678.2.1.1.2.4.1
sipActiveSigners OBJECT-TYPE
    SYNTAX  Integer32
    MAX-ACCESS  read-only
    STATUS  current
    DESCRIPTION "active SIP packet signers"
    ::= { sipSigner 1}

-- 1.3.6.1.4.1.5678.2.1.1.2.4.2
sipTotalSigners OBJECT-TYPE
    SYNTAX  Counter64
    MAX-ACCESS  read-only
    STATUS  current
    DESCRIPTION "total SIP packet signers created"
    ::= { sipSigner 2}

-- 1.3.6.1.4.1.5678.2.1.1.3
popInput OBJECT IDENTIFIER
    ::= { cGateProModule 3}

-- 1.3.6.1.4.1.5678.2.1.1.3.1
popInputActive OBJECT-TYPE
    SYNTAX  Integer32
    MAX-ACCESS  read-only
    STATUS  current
    DESCRIPTION "number of active POP input connections"
    ::= { popInput 1}

-- 1.3.6.1.4.1.5678.2.1.1.3.2
popInputTotal OBJECT-TYPE
    SYNTAX  Integer32
    MAX-ACCESS  read-only
    STATUS  current
    DESCRIPTION "total number of POP input channels"
    ::= { popInput 2}

-- 1.3.6.1.4.1.5678.2.1.1.3.3
popInputJobs OBJECT-TYPE
    SYNTAX  Counter64
    MAX-ACCESS  read-only
    STATUS  current
    DESCRIPTION "total number of POP input connections processed"
    ::= { popInput 3}

-- 1.3.6.1.4.1.5678.2.1.1.3.8
popTrafficIn OBJECT-TYPE
    SYNTAX  Counter64
    MAX-ACCESS  read-only
    STATUS  current
    DESCRIPTION "POP data received"
    ::= { popInput 8}

-- 1.3.6.1.4.1.5678.2.1.1.3.9
popTrafficOut OBJECT-TYPE
    SYNTAX  Counter64
    MAX-ACCESS  read-only
    STATUS  current
    DESCRIPTION "POP data sent"
    ::= { popInput 9}

-- 1.3.6.1.4.1.5678.2.1.1.3.10
popTotalRetrievedMessages OBJECT-TYPE
    SYNTAX  Counter64
    MAX-ACCESS  read-only
    STATUS  current
    DESCRIPTION "total number of retrieved messages"
    ::= { popInput 10}

-- 1.3.6.1.4.1.5678.2.1.1.3.11
popTotalToppedMessages OBJECT-TYPE
    SYNTAX  Counter64
    MAX-ACCESS  read-only
    STATUS  current
    DESCRIPTION "total number of TOP-ed messages"
    ::= { popInput 11}

-- 1.3.6.1.4.1.5678.2.1.1.3.12
popTotalDeletedMessages OBJECT-TYPE
    SYNTAX  Counter64
    MAX-ACCESS  read-only
    STATUS  current
    DESCRIPTION "total number of deleted messages"
    ::= { popInput 12}

-- 1.3.6.1.4.1.5678.2.1.1.3.13
popTotalSubmittedMessages OBJECT-TYPE
    SYNTAX  Counter64
    MAX-ACCESS  read-only
    STATUS  current
    DESCRIPTION "total number of XTND XMIT-ed messages"
    ::= { popInput 13}

-- 1.3.6.1.4.1.5678.2.1.1.3.14
popTotalRetrievedBytes OBJECT-TYPE
    SYNTAX  Counter64
    MAX-ACCESS  read-only
    STATUS  current
    DESCRIPTION "total number of retrieved message bytes"
    ::= { popInput 14}

-- 1.3.6.1.4.1.5678.2.1.1.4
imapInput OBJECT IDENTIFIER
    ::= { cGateProModule 4}

-- 1.3.6.1.4.1.5678.2.1.1.4.1
imapInputActive OBJECT-TYPE
    SYNTAX  Integer32
    MAX-ACCESS  read-only
    STATUS  current
    DESCRIPTION "number of active IMAP input connections"
    ::= { imapInput 1}

-- 1.3.6.1.4.1.5678.2.1.1.4.2
imapInputTotal OBJECT-TYPE
    SYNTAX  Integer32
    MAX-ACCESS  read-only
    STATUS  current
    DESCRIPTION "total number of IMAP input channels"
    ::= { imapInput 2}

-- 1.3.6.1.4.1.5678.2.1.1.4.3
imapInputJobs OBJECT-TYPE
    SYNTAX  Counter64
    MAX-ACCESS  read-only
    STATUS  current
    DESCRIPTION "total number of IMAP input connections processed"
    ::= { imapInput 3}

-- 1.3.6.1.4.1.5678.2.1.1.4.5
imapMAPIActive OBJECT-TYPE
    SYNTAX  Integer32
    MAX-ACCESS  read-only
    STATUS  current
    DESCRIPTION "number of active MAPI sessions"
    ::= { imapInput 5}

-- 1.3.6.1.4.1.5678.2.1.1.4.8
imapTrafficIn OBJECT-TYPE
    SYNTAX  Counter64
    MAX-ACCESS  read-only
    STATUS  current
    DESCRIPTION "IMAP data received"
    ::= { imapInput 8}

-- 1.3.6.1.4.1.5678.2.1.1.4.9
imapTrafficOut OBJECT-TYPE
    SYNTAX  Counter64
    MAX-ACCESS  read-only
    STATUS  current
    DESCRIPTION "IMAP data sent"
    ::= { imapInput 9}

-- 1.3.6.1.4.1.5678.2.1.1.4.10
imapTotalSelectedMailboxes OBJECT-TYPE
    SYNTAX  Counter64
    MAX-ACCESS  read-only
    STATUS  current
    DESCRIPTION "total number of mailboxes selected or examined"
    ::= { imapInput 10}

-- 1.3.6.1.4.1.5678.2.1.1.4.11
imapTotalStatusMailboxes OBJECT-TYPE
    SYNTAX  Counter64
    MAX-ACCESS  read-only
    STATUS  current
    DESCRIPTION "total number of mailboxes checked with the STATUS command"
    ::= { imapInput 11}

-- 1.3.6.1.4.1.5678.2.1.1.4.12
imapTotalFetchedMessages OBJECT-TYPE
    SYNTAX  Counter64
    MAX-ACCESS  read-only
    STATUS  current
    DESCRIPTION "total number of fetched messages"
    ::= { imapInput 12}

-- 1.3.6.1.4.1.5678.2.1.1.4.13
imapTotalStoredMessages OBJECT-TYPE
    SYNTAX  Counter64
    MAX-ACCESS  read-only
    STATUS  current
    DESCRIPTION "total number of message flags modified with the STORE command"
    ::= { imapInput 13}

-- 1.3.6.1.4.1.5678.2.1.1.4.14
imapTotalDeletedMessages OBJECT-TYPE
    SYNTAX  Counter64
    MAX-ACCESS  read-only
    STATUS  current
    DESCRIPTION "total number of deleted messages"
    ::= { imapInput 14}

-- 1.3.6.1.4.1.5678.2.1.1.4.15
imapTotalAppendedMessages OBJECT-TYPE
    SYNTAX  Counter64
    MAX-ACCESS  read-only
    STATUS  current
    DESCRIPTION "total number of appended messages"
    ::= { imapInput 15}

-- 1.3.6.1.4.1.5678.2.1.1.4.16
imapTotalCopiedMessages OBJECT-TYPE
    SYNTAX  Counter64
    MAX-ACCESS  read-only
    STATUS  current
    DESCRIPTION "total number of copied messages"
    ::= { imapInput 16}

-- 1.3.6.1.4.1.5678.2.1.1.4.17
imapTotalParsedMessages OBJECT-TYPE
    SYNTAX  Counter64
    MAX-ACCESS  read-only
    STATUS  current
    DESCRIPTION "total number of parsed messages"
    ::= { imapInput 17}

-- 1.3.6.1.4.1.5678.2.1.1.4.18
imapTotalAttributeUpdates OBJECT-TYPE
    SYNTAX  Counter64
    MAX-ACCESS  read-only
    STATUS  current
    DESCRIPTION "total number of message attribute updates"
    ::= { imapInput 18}

-- 1.3.6.1.4.1.5678.2.1.1.5
httpUserInput OBJECT IDENTIFIER
    ::= { cGateProModule 5}

-- 1.3.6.1.4.1.5678.2.1.1.5.1
httpUserActive OBJECT-TYPE
    SYNTAX  Integer32
    MAX-ACCESS  read-only
    STATUS  current
    DESCRIPTION "number of active HTTP User connections"
    ::= { httpUserInput 1}

-- 1.3.6.1.4.1.5678.2.1.1.5.2
httpUserTotal OBJECT-TYPE
    SYNTAX  Integer32
    MAX-ACCESS  read-only
    STATUS  current
    DESCRIPTION "total number of HTTP User channels"
    ::= { httpUserInput 2}

-- 1.3.6.1.4.1.5678.2.1.1.5.3
httpUserJobs OBJECT-TYPE
    SYNTAX  Counter64
    MAX-ACCESS  read-only
    STATUS  current
    DESCRIPTION "total number of HTTP User connections processed"
    ::= { httpUserInput 3}

-- 1.3.6.1.4.1.5678.2.1.1.5.8
httpUserTrafficIn OBJECT-TYPE
    SYNTAX  Counter64
    MAX-ACCESS  read-only
    STATUS  current
    DESCRIPTION "HTTP User data received"
    ::= { httpUserInput 8}

-- 1.3.6.1.4.1.5678.2.1.1.5.9
httpUserTrafficOut OBJECT-TYPE
    SYNTAX  Counter64
    MAX-ACCESS  read-only
    STATUS  current
    DESCRIPTION "HTTP User data sent"
    ::= { httpUserInput 9}

-- 1.3.6.1.4.1.5678.2.1.1.5.10
httpUserRequestsProcessed OBJECT-TYPE
    SYNTAX  Counter64
    MAX-ACCESS  read-only
    STATUS  current
    DESCRIPTION "total number of HTTP User requests processed"
    ::= { httpUserInput 10}

-- 1.3.6.1.4.1.5678.2.1.1.5.11
httpUserAuthSucceeded OBJECT-TYPE
    SYNTAX  Counter64
    MAX-ACCESS  read-only
    STATUS  current
    DESCRIPTION "total number of successful HTTP User Authentication requests"
    ::= { httpUserInput 11}

-- 1.3.6.1.4.1.5678.2.1.1.5.12
httpUserAuthFailed OBJECT-TYPE
    SYNTAX  Counter64
    MAX-ACCESS  read-only
    STATUS  current
    DESCRIPTION "total number of failed HTTP User Authentication requests"
    ::= { httpUserInput 12}

-- 1.3.6.1.4.1.5678.2.1.1.5.13
httpUserCGIRequestsProcessed OBJECT-TYPE
    SYNTAX  Counter64
    MAX-ACCESS  read-only
    STATUS  current
    DESCRIPTION "total number of User CGI requests processed"
    ::= { httpUserInput 13}

-- 1.3.6.1.4.1.5678.2.1.1.5.14
httpUserNotFound OBJECT-TYPE
    SYNTAX  Counter64
    MAX-ACCESS  read-only
    STATUS  current
    DESCRIPTION "total number of HTTP User not-found errors"
    ::= { httpUserInput 14}

-- 1.3.6.1.4.1.5678.2.1.1.6
localDelivery OBJECT IDENTIFIER
    ::= { cGateProModule 6}

-- 1.3.6.1.4.1.5678.2.1.1.6.1
localDeliveryActive OBJECT-TYPE
    SYNTAX  Integer32
    MAX-ACCESS  read-only
    STATUS  current
    DESCRIPTION "number of active local delivery queues (accounts)"
    ::= { localDelivery 1}

-- 1.3.6.1.4.1.5678.2.1.1.6.2
localDeliveryWaiting OBJECT-TYPE
    SYNTAX  Integer32
    MAX-ACCESS  read-only
    STATUS  current
    DESCRIPTION "number of waiting local delivery queues (accounts)"
    ::= { localDelivery 2}

-- 1.3.6.1.4.1.5678.2.1.1.6.10
localDeliveryDeliveredMessages OBJECT-TYPE
    SYNTAX  Counter64
    MAX-ACCESS  read-only
    STATUS  current
    DESCRIPTION "total number of delivered messages"
    ::= { localDelivery 10}

-- 1.3.6.1.4.1.5678.2.1.1.6.11
localDeliveryFailedMessages OBJECT-TYPE
    SYNTAX  Counter64
    MAX-ACCESS  read-only
    STATUS  current
    DESCRIPTION "total number of failed messages"
    ::= { localDelivery 11}

-- 1.3.6.1.4.1.5678.2.1.1.6.12
localDeliveryDeliveredBytes OBJECT-TYPE
    SYNTAX  Counter64
    MAX-ACCESS  read-only
    STATUS  current
    DESCRIPTION "total size of delivered messages"
    ::= { localDelivery 12}

-- 1.3.6.1.4.1.5678.2.1.1.7
ftpInput OBJECT IDENTIFIER
    ::= { cGateProModule 7}

-- 1.3.6.1.4.1.5678.2.1.1.7.1
ftpInputActive OBJECT-TYPE
    SYNTAX  Integer32
    MAX-ACCESS  read-only
    STATUS  current
    DESCRIPTION "number of active FTP input connections"
    ::= { ftpInput 1}

-- 1.3.6.1.4.1.5678.2.1.1.7.2
ftpInputTotal OBJECT-TYPE
    SYNTAX  Integer32
    MAX-ACCESS  read-only
    STATUS  current
    DESCRIPTION "total number of FTP input channels"
    ::= { ftpInput 2}

-- 1.3.6.1.4.1.5678.2.1.1.7.3
ftpInputJobs OBJECT-TYPE
    SYNTAX  Counter64
    MAX-ACCESS  read-only
    STATUS  current
    DESCRIPTION "total number of FTP input connections processed"
    ::= { ftpInput 3}

-- 1.3.6.1.4.1.5678.2.1.1.7.8
ftpTrafficIn OBJECT-TYPE
    SYNTAX  Counter64
    MAX-ACCESS  read-only
    STATUS  current
    DESCRIPTION "FTP control data received"
    ::= { ftpInput 8}

-- 1.3.6.1.4.1.5678.2.1.1.7.9
ftpTrafficOut OBJECT-TYPE
    SYNTAX  Counter64
    MAX-ACCESS  read-only
    STATUS  current
    DESCRIPTION "FTP control data sent"
    ::= { ftpInput 9}

-- 1.3.6.1.4.1.5678.2.1.1.7.10
ftpTotalRetrievedFiles OBJECT-TYPE
    SYNTAX  Counter64
    MAX-ACCESS  read-only
    STATUS  current
    DESCRIPTION "total number of retrieved files"
    ::= { ftpInput 10}

-- 1.3.6.1.4.1.5678.2.1.1.7.11
ftpTotalUploadedFiles OBJECT-TYPE
    SYNTAX  Counter64
    MAX-ACCESS  read-only
    STATUS  current
    DESCRIPTION "total number of uploaded files"
    ::= { ftpInput 11}

-- 1.3.6.1.4.1.5678.2.1.1.7.12
ftpTotalDeletedFiles OBJECT-TYPE
    SYNTAX  Counter64
    MAX-ACCESS  read-only
    STATUS  current
    DESCRIPTION "total number of deleted files"
    ::= { ftpInput 12}

-- 1.3.6.1.4.1.5678.2.1.1.7.13
ftpTotalRenamedFiles OBJECT-TYPE
    SYNTAX  Counter64
    MAX-ACCESS  read-only
    STATUS  current
    DESCRIPTION "total number of renamed files"
    ::= { ftpInput 13}

-- 1.3.6.1.4.1.5678.2.1.1.7.14
ftpTotalRetrievedBytes OBJECT-TYPE
    SYNTAX  Counter64
    MAX-ACCESS  read-only
    STATUS  current
    DESCRIPTION "total size of retrieved files"
    ::= { ftpInput 14}

-- 1.3.6.1.4.1.5678.2.1.1.7.15
ftpTotalUploadedBytes OBJECT-TYPE
    SYNTAX  Counter64
    MAX-ACCESS  read-only
    STATUS  current
    DESCRIPTION "total size of uploaded files"
    ::= { ftpInput 15}

-- 1.3.6.1.4.1.5678.2.1.1.7.16
ftpTotalListInfoBytes OBJECT-TYPE
    SYNTAX  Counter64
    MAX-ACCESS  read-only
    STATUS  current
    DESCRIPTION "total size of dictectory listings sent"
    ::= { ftpInput 16}

-- 1.3.6.1.4.1.5678.2.1.1.8
rpop OBJECT IDENTIFIER
    ::= { cGateProModule 8}

-- 1.3.6.1.4.1.5678.2.1.1.8.1
rpopActive OBJECT-TYPE
    SYNTAX  Integer32
    MAX-ACCESS  read-only
    STATUS  current
    DESCRIPTION "number of active RPOP polling connections"
    ::= { rpop 1}

-- 1.3.6.1.4.1.5678.2.1.1.8.2
rpopTotal OBJECT-TYPE
    SYNTAX  Integer32
    MAX-ACCESS  read-only
    STATUS  current
    DESCRIPTION "total number of RPOP polling channels"
    ::= { rpop 2}

-- 1.3.6.1.4.1.5678.2.1.1.8.3
rpopJobs OBJECT-TYPE
    SYNTAX  Counter64
    MAX-ACCESS  read-only
    STATUS  current
    DESCRIPTION "total number of RPOP polling connections processed"
    ::= { rpop 3}

-- 1.3.6.1.4.1.5678.2.1.1.8.8
rpopTrafficIn OBJECT-TYPE
    SYNTAX  Counter64
    MAX-ACCESS  read-only
    STATUS  current
    DESCRIPTION "RPOP data received"
    ::= { rpop 8}

-- 1.3.6.1.4.1.5678.2.1.1.8.9
rpopTrafficOut OBJECT-TYPE
    SYNTAX  Counter64
    MAX-ACCESS  read-only
    STATUS  current
    DESCRIPTION "RPOP data sent"
    ::= { rpop 9}

-- 1.3.6.1.4.1.5678.2.1.1.8.10
rpopMessagesRetrieved OBJECT-TYPE
    SYNTAX  Counter64
    MAX-ACCESS  read-only
    STATUS  current
    DESCRIPTION "total number of RPOP messages retrieved"
    ::= { rpop 10}

-- 1.3.6.1.4.1.5678.2.1.1.8.11
rpopMessageBytesRetrieved OBJECT-TYPE
    SYNTAX  Counter64
    MAX-ACCESS  read-only
    STATUS  current
    DESCRIPTION "total size of RPOP messages retrieved"
    ::= { rpop 11}

-- 1.3.6.1.4.1.5678.2.1.1.8.12
rpopFailedConnections OBJECT-TYPE
    SYNTAX  Counter64
    MAX-ACCESS  read-only
    STATUS  current
    DESCRIPTION "total number of failed RPOP connections"
    ::= { rpop 12}

-- 1.3.6.1.4.1.5678.2.1.1.8.13
rpopFailedLogins OBJECT-TYPE
    SYNTAX  Counter64
    MAX-ACCESS  read-only
    STATUS  current
    DESCRIPTION "total number of failed RPOP authentication operations"
    ::= { rpop 13}

-- 1.3.6.1.4.1.5678.2.1.1.8.14
rpopFailedSessions OBJECT-TYPE
    SYNTAX  Counter64
    MAX-ACCESS  read-only
    STATUS  current
    DESCRIPTION "total number of failed RPOP retrieval sessions"
    ::= { rpop 14}

-- 1.3.6.1.4.1.5678.2.1.1.8.17
rpopConnectionsMade OBJECT-TYPE
    SYNTAX  Counter64
    MAX-ACCESS  read-only
    STATUS  current
    DESCRIPTION "established RPOP connections"
    ::= { rpop 17}

-- 1.3.6.1.4.1.5678.2.1.1.8.18
rpopConnectionsFailed OBJECT-TYPE
    SYNTAX  Counter64
    MAX-ACCESS  read-only
    STATUS  current
    DESCRIPTION "failed RPOP connection attempts"
    ::= { rpop 18}

-- 1.3.6.1.4.1.5678.2.1.1.9
ldapInput OBJECT IDENTIFIER
    ::= { cGateProModule 9}

-- 1.3.6.1.4.1.5678.2.1.1.9.1
ldapInputActive OBJECT-TYPE
    SYNTAX  Integer32
    MAX-ACCESS  read-only
    STATUS  current
    DESCRIPTION "number of active LDAP input connections"
    ::= { ldapInput 1}

-- 1.3.6.1.4.1.5678.2.1.1.9.2
ldapInputTotal OBJECT-TYPE
    SYNTAX  Integer32
    MAX-ACCESS  read-only
    STATUS  current
    DESCRIPTION "total number of LDAP input channels"
    ::= { ldapInput 2}

-- 1.3.6.1.4.1.5678.2.1.1.9.3
ldapInputJobs OBJECT-TYPE
    SYNTAX  Counter64
    MAX-ACCESS  read-only
    STATUS  current
    DESCRIPTION "total number of LDAP input connections processed"
    ::= { ldapInput 3}

-- 1.3.6.1.4.1.5678.2.1.1.9.8
ldapTrafficIn OBJECT-TYPE
    SYNTAX  Counter64
    MAX-ACCESS  read-only
    STATUS  current
    DESCRIPTION "LDAP data received"
    ::= { ldapInput 8}

-- 1.3.6.1.4.1.5678.2.1.1.9.9
ldapTrafficOut OBJECT-TYPE
    SYNTAX  Counter64
    MAX-ACCESS  read-only
    STATUS  current
    DESCRIPTION "LDAP data sent"
    ::= { ldapInput 9}

-- 1.3.6.1.4.1.5678.2.1.1.10
ximssInput OBJECT IDENTIFIER
    ::= { cGateProModule 10}

-- 1.3.6.1.4.1.5678.2.1.1.10.1
ximssInputActive OBJECT-TYPE
    SYNTAX  Integer32
    MAX-ACCESS  read-only
    STATUS  current
    DESCRIPTION "number of active XIMSS input connections"
    ::= { ximssInput 1}

-- 1.3.6.1.4.1.5678.2.1.1.10.2
ximssInputTotal OBJECT-TYPE
    SYNTAX  Integer32
    MAX-ACCESS  read-only
    STATUS  current
    DESCRIPTION "total number of XIMSS input channels"
    ::= { ximssInput 2}

-- 1.3.6.1.4.1.5678.2.1.1.10.3
ximssInputJobs OBJECT-TYPE
    SYNTAX  Counter64
    MAX-ACCESS  read-only
    STATUS  current
    DESCRIPTION "total number of XIMSS input connections processed"
    ::= { ximssInput 3}

-- 1.3.6.1.4.1.5678.2.1.1.10.8
ximssTrafficIn OBJECT-TYPE
    SYNTAX  Counter64
    MAX-ACCESS  read-only
    STATUS  current
    DESCRIPTION "XIMSS data received"
    ::= { ximssInput 8}

-- 1.3.6.1.4.1.5678.2.1.1.10.9
ximssTrafficOut OBJECT-TYPE
    SYNTAX  Counter64
    MAX-ACCESS  read-only
    STATUS  current
    DESCRIPTION "XIMSS data sent"
    ::= { ximssInput 9}

-- 1.3.6.1.4.1.5678.2.1.1.10.10
ximssTotalRequests OBJECT-TYPE
    SYNTAX  Counter64
    MAX-ACCESS  read-only
    STATUS  current
    DESCRIPTION "total number of XIMSS requests processed"
    ::= { ximssInput 10}

-- 1.3.6.1.4.1.5678.2.1.1.11
xmpp OBJECT IDENTIFIER
    ::= { cGateProModule 11}

-- 1.3.6.1.4.1.5678.2.1.1.11.1
xmppInput OBJECT IDENTIFIER
    ::= { xmpp 1}

-- 1.3.6.1.4.1.5678.2.1.1.11.1.1
xmppInputActive OBJECT-TYPE
    SYNTAX  Integer32
    MAX-ACCESS  read-only
    STATUS  current
    DESCRIPTION "number of active XMPP input connections"
    ::= { xmppInput 1}

-- 1.3.6.1.4.1.5678.2.1.1.11.1.2
xmppInputTotal OBJECT-TYPE
    SYNTAX  Integer32
    MAX-ACCESS  read-only
    STATUS  current
    DESCRIPTION "total number of XMPP input channels"
    ::= { xmppInput 2}

-- 1.3.6.1.4.1.5678.2.1.1.11.1.3
xmppInputJobs OBJECT-TYPE
    SYNTAX  Counter64
    MAX-ACCESS  read-only
    STATUS  current
    DESCRIPTION "total number of XMPP input connections processed"
    ::= { xmppInput 3}

-- 1.3.6.1.4.1.5678.2.1.1.11.1.8
xmppInputTrafficIn OBJECT-TYPE
    SYNTAX  Counter64
    MAX-ACCESS  read-only
    STATUS  current
    DESCRIPTION "XMPP input channel data received"
    ::= { xmppInput 8}

-- 1.3.6.1.4.1.5678.2.1.1.11.1.9
xmppInputTrafficOut OBJECT-TYPE
    SYNTAX  Counter64
    MAX-ACCESS  read-only
    STATUS  current
    DESCRIPTION "XMPP input channel data sent"
    ::= { xmppInput 9}

-- 1.3.6.1.4.1.5678.2.1.1.11.2
xmppOutput OBJECT IDENTIFIER
    ::= { xmpp 2}

-- 1.3.6.1.4.1.5678.2.1.1.11.2.1
xmppOutputActive OBJECT-TYPE
    SYNTAX  Integer32
    MAX-ACCESS  read-only
    STATUS  current
    DESCRIPTION "number of active XMPP output connections"
    ::= { xmppOutput 1}

-- 1.3.6.1.4.1.5678.2.1.1.11.2.2
xmppOutputTotal OBJECT-TYPE
    SYNTAX  Integer32
    MAX-ACCESS  read-only
    STATUS  current
    DESCRIPTION "total number of XMPP output channels"
    ::= { xmppOutput 2}

-- 1.3.6.1.4.1.5678.2.1.1.11.2.3
xmppOutputJobs OBJECT-TYPE
    SYNTAX  Counter64
    MAX-ACCESS  read-only
    STATUS  current
    DESCRIPTION "total number of XMPP output connections processed"
    ::= { xmppOutput 3}

-- 1.3.6.1.4.1.5678.2.1.1.11.2.8
xmppOutputTrafficIn OBJECT-TYPE
    SYNTAX  Counter64
    MAX-ACCESS  read-only
    STATUS  current
    DESCRIPTION "XMPP output channel data received"
    ::= { xmppOutput 8}

-- 1.3.6.1.4.1.5678.2.1.1.11.2.9
xmppOutputTrafficOut OBJECT-TYPE
    SYNTAX  Counter64
    MAX-ACCESS  read-only
    STATUS  current
    DESCRIPTION "XMPP output channel data sent"
    ::= { xmppOutput 9}

-- 1.3.6.1.4.1.5678.2.1.1.11.2.13
xmppOutputConnectionsMade OBJECT-TYPE
    SYNTAX  Counter64
    MAX-ACCESS  read-only
    STATUS  current
    DESCRIPTION "outgoing XMPP: established connections"
    ::= { xmppOutput 13}

-- 1.3.6.1.4.1.5678.2.1.1.11.2.14
xmppOutputConnectionsFailed OBJECT-TYPE
    SYNTAX  Counter64
    MAX-ACCESS  read-only
    STATUS  current
    DESCRIPTION "outgoing XMPP: failed connections"
    ::= { xmppOutput 14}

-- 1.3.6.1.4.1.5678.2.1.1.12
smpp OBJECT IDENTIFIER
    ::= { cGateProModule 12}

-- 1.3.6.1.4.1.5678.2.1.1.12.1
smppMessagesSent OBJECT-TYPE
    SYNTAX  Counter64
    MAX-ACCESS  read-only
    STATUS  current
    DESCRIPTION "SMPP messages sent"
    ::= { smpp 1}

-- 1.3.6.1.4.1.5678.2.1.1.12.2
smppMessagesReceived OBJECT-TYPE
    SYNTAX  Counter64
    MAX-ACCESS  read-only
    STATUS  current
    DESCRIPTION "SMPP messages received"
    ::= { smpp 2}

-- 1.3.6.1.4.1.5678.2.1.1.12.5
smppConnectionsFailed OBJECT-TYPE
    SYNTAX  Counter64
    MAX-ACCESS  read-only
    STATUS  current
    DESCRIPTION "SMPP connections failed"
    ::= { smpp 5}

-- 1.3.6.1.4.1.5678.2.1.1.12.6
smppConnectionsMade OBJECT-TYPE
    SYNTAX  Counter64
    MAX-ACCESS  read-only
    STATUS  current
    DESCRIPTION "SMPP connections made"
    ::= { smpp 6}

-- 1.3.6.1.4.1.5678.2.1.1.12.8
smppTrafficIn OBJECT-TYPE
    SYNTAX  Counter64
    MAX-ACCESS  read-only
    STATUS  current
    DESCRIPTION "SMPP data received"
    ::= { smpp 8}

-- 1.3.6.1.4.1.5678.2.1.1.12.9
smppTrafficOut OBJECT-TYPE
    SYNTAX  Counter64
    MAX-ACCESS  read-only
    STATUS  current
    DESCRIPTION "SMPP data sent"
    ::= { smpp 9}

-- 1.3.6.1.4.1.5678.2.1.1.15
airSync OBJECT IDENTIFIER
    ::= { cGateProModule 15}

-- 1.3.6.1.4.1.5678.2.1.1.15.1
airSyncActive OBJECT-TYPE
    SYNTAX  Integer32
    MAX-ACCESS  read-only
    STATUS  current
    DESCRIPTION "number of active AirSync requests"
    ::= { airSync 1}

-- 1.3.6.1.4.1.5678.2.1.1.15.2
airSyncTotal OBJECT-TYPE
    SYNTAX  Counter64
    MAX-ACCESS  read-only
    STATUS  current
    DESCRIPTION "total number of AirSync requests processed"
    ::= { airSync 2}

-- 1.3.6.1.4.1.5678.2.1.1.15.8
airSyncTrafficIn OBJECT-TYPE
    SYNTAX  Counter64
    MAX-ACCESS  read-only
    STATUS  current
    DESCRIPTION "AirSync data received"
    ::= { airSync 8}

-- 1.3.6.1.4.1.5678.2.1.1.15.9
airSyncTrafficOut OBJECT-TYPE
    SYNTAX  Counter64
    MAX-ACCESS  read-only
    STATUS  current
    DESCRIPTION "AirSync data sent"
    ::= { airSync 9}

-- 1.3.6.1.4.1.5678.2.1.1.15.10
airMessagesSubmitted OBJECT-TYPE
    SYNTAX  Counter64
    MAX-ACCESS  read-only
    STATUS  current
    DESCRIPTION "total number of messages submitted via AirSync"
    ::= { airSync 10}

-- 1.3.6.1.4.1.5678.2.1.1.15.11
airMessagesAdded OBJECT-TYPE
    SYNTAX  Counter64
    MAX-ACCESS  read-only
    STATUS  current
    DESCRIPTION "total number of messages added via AirSync"
    ::= { airSync 11}

-- 1.3.6.1.4.1.5678.2.1.1.15.12
airMessagesChanged OBJECT-TYPE
    SYNTAX  Counter64
    MAX-ACCESS  read-only
    STATUS  current
    DESCRIPTION "total number of messages changed via AirSync"
    ::= { airSync 12}

-- 1.3.6.1.4.1.5678.2.1.1.15.13
airMessagesDeleted OBJECT-TYPE
    SYNTAX  Counter64
    MAX-ACCESS  read-only
    STATUS  current
    DESCRIPTION "total number of messages deleted via AirSync"
    ::= { airSync 13}

-- 1.3.6.1.4.1.5678.2.1.1.15.14
airMessagesFetched OBJECT-TYPE
    SYNTAX  Counter64
    MAX-ACCESS  read-only
    STATUS  current
    DESCRIPTION "total number of messages fetched via AirSync"
    ::= { airSync 14}

-- 1.3.6.1.4.1.5678.2.1.1.15.15
airMessagesRetrieved OBJECT-TYPE
    SYNTAX  Counter64
    MAX-ACCESS  read-only
    STATUS  current
    DESCRIPTION "total number of messages retrieved via AirSync"
    ::= { airSync 15}

-- 1.3.6.1.4.1.5678.2.1.1.20
radius OBJECT IDENTIFIER
    ::= { cGateProModule 20}

-- 1.3.6.1.4.1.5678.2.1.1.20.1
radiusInputPackets OBJECT-TYPE
    SYNTAX  Counter64
    MAX-ACCESS  read-only
    STATUS  current
    DESCRIPTION "RADIUS packets received"
    ::= { radius 1}

-- 1.3.6.1.4.1.5678.2.1.1.20.2
radiusOutputPackets OBJECT-TYPE
    SYNTAX  Counter64
    MAX-ACCESS  read-only
    STATUS  current
    DESCRIPTION "RADIUS packets sent"
    ::= { radius 2}

-- 1.3.6.1.4.1.5678.2.1.1.20.3
radiusInputTraffic OBJECT-TYPE
    SYNTAX  Counter64
    MAX-ACCESS  read-only
    STATUS  current
    DESCRIPTION "RADIUS data received"
    ::= { radius 3}

-- 1.3.6.1.4.1.5678.2.1.1.20.4
radiusOutputTraffic OBJECT-TYPE
    SYNTAX  Counter64
    MAX-ACCESS  read-only
    STATUS  current
    DESCRIPTION "RADIUS data sent"
    ::= { radius 4}

-- 1.3.6.1.4.1.5678.2.1.1.20.5
radiusInputErrors OBJECT-TYPE
    SYNTAX  Counter64
    MAX-ACCESS  read-only
    STATUS  current
    DESCRIPTION "RADIUS receiving errors"
    ::= { radius 5}

-- 1.3.6.1.4.1.5678.2.1.1.20.6
radiusOutputErrors OBJECT-TYPE
    SYNTAX  Counter64
    MAX-ACCESS  read-only
    STATUS  current
    DESCRIPTION "RADIUS sending errors"
    ::= { radius 6}

-- 1.3.6.1.4.1.5678.2.1.1.20.10
radiusTotalAuth OBJECT-TYPE
    SYNTAX  Counter64
    MAX-ACCESS  read-only
    STATUS  current
    DESCRIPTION "total number of RADIUS AUTH requests"
    ::= { radius 10}

-- 1.3.6.1.4.1.5678.2.1.1.20.11
radiusFailedAuth OBJECT-TYPE
    SYNTAX  Counter64
    MAX-ACCESS  read-only
    STATUS  current
    DESCRIPTION "total number of failed AUTH requests"
    ::= { radius 11}

-- 1.3.6.1.4.1.5678.2.1.1.21
tftp OBJECT IDENTIFIER
    ::= { cGateProModule 21}

-- 1.3.6.1.4.1.5678.2.1.1.21.1
tftpInputPackets OBJECT-TYPE
    SYNTAX  Counter64
    MAX-ACCESS  read-only
    STATUS  current
    DESCRIPTION "TFTP packets received"
    ::= { tftp 1}

-- 1.3.6.1.4.1.5678.2.1.1.21.2
tftpOutputPackets OBJECT-TYPE
    SYNTAX  Counter64
    MAX-ACCESS  read-only
    STATUS  current
    DESCRIPTION "TFTP packets sent"
    ::= { tftp 2}

-- 1.3.6.1.4.1.5678.2.1.1.21.3
tftpInputTraffic OBJECT-TYPE
    SYNTAX  Counter64
    MAX-ACCESS  read-only
    STATUS  current
    DESCRIPTION "TFTP data received"
    ::= { tftp 3}

-- 1.3.6.1.4.1.5678.2.1.1.21.4
tftpOutputTraffic OBJECT-TYPE
    SYNTAX  Counter64
    MAX-ACCESS  read-only
    STATUS  current
    DESCRIPTION "TFTP data sent"
    ::= { tftp 4}

-- 1.3.6.1.4.1.5678.2.1.1.21.5
tftpInputErrors OBJECT-TYPE
    SYNTAX  Counter64
    MAX-ACCESS  read-only
    STATUS  current
    DESCRIPTION "TFTP receiving errors"
    ::= { tftp 5}

-- 1.3.6.1.4.1.5678.2.1.1.21.6
tftpOutputErrors OBJECT-TYPE
    SYNTAX  Counter64
    MAX-ACCESS  read-only
    STATUS  current
    DESCRIPTION "TFTP sending errors"
    ::= { tftp 6}

-- 1.3.6.1.4.1.5678.2.1.1.21.10
tftpCurrentSessions OBJECT-TYPE
    SYNTAX  Integer32
    MAX-ACCESS  read-only
    STATUS  current
    DESCRIPTION "current number of TFTP sessions"
    ::= { tftp 10}

-- 1.3.6.1.4.1.5678.2.1.1.21.11
tftpTotalSessions OBJECT-TYPE
    SYNTAX  Counter64
    MAX-ACCESS  read-only
    STATUS  current
    DESCRIPTION "total number of TFTP sessions"
    ::= { tftp 11}

-- 1.3.6.1.4.1.5678.2.1.1.30
httpAdminInput OBJECT IDENTIFIER
    ::= { cGateProModule 30}

-- 1.3.6.1.4.1.5678.2.1.1.30.1
httpAdminActive OBJECT-TYPE
    SYNTAX  Integer32
    MAX-ACCESS  read-only
    STATUS  current
    DESCRIPTION "number of active HTTP Admin connections"
    ::= { httpAdminInput 1}

-- 1.3.6.1.4.1.5678.2.1.1.30.2
httpAdminTotal OBJECT-TYPE
    SYNTAX  Integer32
    MAX-ACCESS  read-only
    STATUS  current
    DESCRIPTION "total number of HTTP Admin channels"
    ::= { httpAdminInput 2}

-- 1.3.6.1.4.1.5678.2.1.1.30.3
httpAdminJobs OBJECT-TYPE
    SYNTAX  Counter64
    MAX-ACCESS  read-only
    STATUS  current
    DESCRIPTION "total number of HTTP Admin connections processed"
    ::= { httpAdminInput 3}

-- 1.3.6.1.4.1.5678.2.1.1.30.8
httpAdminTrafficIn OBJECT-TYPE
    SYNTAX  Counter64
    MAX-ACCESS  read-only
    STATUS  current
    DESCRIPTION "HTTP Admin data received"
    ::= { httpAdminInput 8}

-- 1.3.6.1.4.1.5678.2.1.1.30.9
httpAdminTrafficOut OBJECT-TYPE
    SYNTAX  Counter64
    MAX-ACCESS  read-only
    STATUS  current
    DESCRIPTION "HTTP Admin data sent"
    ::= { httpAdminInput 9}

-- 1.3.6.1.4.1.5678.2.1.1.30.10
httpAdminRequestsProcessed OBJECT-TYPE
    SYNTAX  Counter64
    MAX-ACCESS  read-only
    STATUS  current
    DESCRIPTION "total number of HTTP Admin requests processed"
    ::= { httpAdminInput 10}

-- 1.3.6.1.4.1.5678.2.1.1.30.11
httpAdminAuthSucceeded OBJECT-TYPE
    SYNTAX  Counter64
    MAX-ACCESS  read-only
    STATUS  current
    DESCRIPTION "total number of successful HTTP Admin Authentication requests"
    ::= { httpAdminInput 11}

-- 1.3.6.1.4.1.5678.2.1.1.30.12
httpAdminAuthFailed OBJECT-TYPE
    SYNTAX  Counter64
    MAX-ACCESS  read-only
    STATUS  current
    DESCRIPTION "total number of failed HTTP Admin Authentication requests"
    ::= { httpAdminInput 12}

-- 1.3.6.1.4.1.5678.2.1.1.30.13
httpAdminCGIRequestsProcessed OBJECT-TYPE
    SYNTAX  Counter64
    MAX-ACCESS  read-only
    STATUS  current
    DESCRIPTION "total number of Admin CGI requests processed"
    ::= { httpAdminInput 13}

-- 1.3.6.1.4.1.5678.2.1.1.30.14
httpAdminNotFound OBJECT-TYPE
    SYNTAX  Counter64
    MAX-ACCESS  read-only
    STATUS  current
    DESCRIPTION "total number of HTTP User not-found errors"
    ::= { httpAdminInput 14}

-- 1.3.6.1.4.1.5678.2.1.1.31
pwdInput OBJECT IDENTIFIER
    ::= { cGateProModule 31}

-- 1.3.6.1.4.1.5678.2.1.1.31.1
pwdInputActive OBJECT-TYPE
    SYNTAX  Integer32
    MAX-ACCESS  read-only
    STATUS  current
    DESCRIPTION "number of active PWD input connections"
    ::= { pwdInput 1}

-- 1.3.6.1.4.1.5678.2.1.1.31.2
pwdInputTotal OBJECT-TYPE
    SYNTAX  Integer32
    MAX-ACCESS  read-only
    STATUS  current
    DESCRIPTION "total number of PWD input channels"
    ::= { pwdInput 2}

-- 1.3.6.1.4.1.5678.2.1.1.31.3
pwdInputJobs OBJECT-TYPE
    SYNTAX  Counter64
    MAX-ACCESS  read-only
    STATUS  current
    DESCRIPTION "total number of PWD input connections processed"
    ::= { pwdInput 3}

-- 1.3.6.1.4.1.5678.2.1.1.31.8
pwdTrafficIn OBJECT-TYPE
    SYNTAX  Counter64
    MAX-ACCESS  read-only
    STATUS  current
    DESCRIPTION "PWD data received"
    ::= { pwdInput 8}

-- 1.3.6.1.4.1.5678.2.1.1.31.9
pwdTrafficOut OBJECT-TYPE
    SYNTAX  Counter64
    MAX-ACCESS  read-only
    STATUS  current
    DESCRIPTION "PWD data sent"
    ::= { pwdInput 9}

-- 1.3.6.1.4.1.5678.2.1.1.31.10
pwdTotalCommandsProcessed OBJECT-TYPE
    SYNTAX  Counter64
    MAX-ACCESS  read-only
    STATUS  current
    DESCRIPTION "total number of PWD/CLI commands processed"
    ::= { pwdInput 10}

-- 1.3.6.1.4.1.5678.2.1.2
cGateProQueue OBJECT IDENTIFIER
    ::= { cGateProObject 2}

-- 1.3.6.1.4.1.5678.2.1.2.1
numQueuedMessages OBJECT-TYPE
    SYNTAX  Integer32
    MAX-ACCESS  read-only
    STATUS  current
    DESCRIPTION "current number of enqueued messages"
    ::= { cGateProQueue 1}

-- 1.3.6.1.4.1.5678.2.1.2.2
numOpenedMessages OBJECT-TYPE
    SYNTAX  Integer32
    MAX-ACCESS  read-only
    STATUS  current
    DESCRIPTION "current number of opened messages"
    ::= { cGateProQueue 2}

-- 1.3.6.1.4.1.5678.2.1.2.3
totalSubmittedMessages OBJECT-TYPE
    SYNTAX  Counter64
    MAX-ACCESS  read-only
    STATUS  current
    DESCRIPTION "total number of submitted messages"
    ::= { cGateProQueue 3}

-- 1.3.6.1.4.1.5678.2.1.2.4
totalBadMessages OBJECT-TYPE
    SYNTAX  Counter64
    MAX-ACCESS  read-only
    STATUS  current
    DESCRIPTION "total number of bad messages"
    ::= { cGateProQueue 4}

-- 1.3.6.1.4.1.5678.2.1.2.5
totalDeletedMessages OBJECT-TYPE
    SYNTAX  Counter64
    MAX-ACCESS  read-only
    STATUS  current
    DESCRIPTION "total number of processed (and deleted) messages"
    ::= { cGateProQueue 5}

-- 1.3.6.1.4.1.5678.2.1.2.6
numEnqueuerMessages OBJECT-TYPE
    SYNTAX  Integer32
    MAX-ACCESS  read-only
    STATUS  current
    DESCRIPTION "current number of submitted, but not yet enqueued messages"
    ::= { cGateProQueue 6}

-- 1.3.6.1.4.1.5678.2.1.2.7
numDequeuerBatches OBJECT-TYPE
    SYNTAX  Integer32
    MAX-ACCESS  read-only
    STATUS  current
    DESCRIPTION "current number of unprocessed dequeuer batches"
    ::= { cGateProQueue 7}

-- 1.3.6.1.4.1.5678.2.1.2.8
numDequeuerActiveProcessors OBJECT-TYPE
    SYNTAX  Integer32
    MAX-ACCESS  read-only
    STATUS  current
    DESCRIPTION "current number of active dequeuer processors"
    ::= { cGateProQueue 8}

-- 1.3.6.1.4.1.5678.2.1.2.9
numEnqueuerActiveProcessors OBJECT-TYPE
    SYNTAX  Integer32
    MAX-ACCESS  read-only
    STATUS  current
    DESCRIPTION "current number of active enqueuer processors"
    ::= { cGateProQueue 9}

-- 1.3.6.1.4.1.5678.2.1.2.20
totalFailedRecipients OBJECT-TYPE
    SYNTAX  Counter64
    MAX-ACCESS  read-only
    STATUS  current
    DESCRIPTION "total number of failed deliveries (recipients)"
    ::= { cGateProQueue 20}

-- 1.3.6.1.4.1.5678.2.1.2.21
totalRelayedRecipients OBJECT-TYPE
    SYNTAX  Counter64
    MAX-ACCESS  read-only
    STATUS  current
    DESCRIPTION "total number of relayed deliveries (recipients)"
    ::= { cGateProQueue 21}

-- 1.3.6.1.4.1.5678.2.1.2.22
totalDeliveredRecipients OBJECT-TYPE
    SYNTAX  Counter64
    MAX-ACCESS  read-only
    STATUS  current
    DESCRIPTION "total number of final deliveries (recipients)"
    ::= { cGateProQueue 22}

-- 1.3.6.1.4.1.5678.2.1.2.23
totalDelayedRecipients OBJECT-TYPE
    SYNTAX  Counter64
    MAX-ACCESS  read-only
    STATUS  current
    DESCRIPTION "total number of delayed deliveries (recipients)"
    ::= { cGateProQueue 23}

-- 1.3.6.1.4.1.5678.2.1.2.27
totalMailErrorReports OBJECT-TYPE
    SYNTAX  Counter64
    MAX-ACCESS  read-only
    STATUS  current
    DESCRIPTION "total number of error reports generated"
    ::= { cGateProQueue 27}

-- 1.3.6.1.4.1.5678.2.1.2.28
totalMailDeliveryReports OBJECT-TYPE
    SYNTAX  Counter64
    MAX-ACCESS  read-only
    STATUS  current
    DESCRIPTION "total number of delivery reports generated"
    ::= { cGateProQueue 28}

-- 1.3.6.1.4.1.5678.2.1.2.29
totalMailWarningReports OBJECT-TYPE
    SYNTAX  Counter64
    MAX-ACCESS  read-only
    STATUS  current
    DESCRIPTION "total number of warning reports generated"
    ::= { cGateProQueue 29}

-- 1.3.6.1.4.1.5678.2.1.3
userSessions OBJECT IDENTIFIER
    ::= { cGateProObject 3}

-- 1.3.6.1.4.1.5678.2.1.3.1
userSessionsOpen OBJECT-TYPE
    SYNTAX  Integer32
    MAX-ACCESS  read-only
    STATUS  current
    DESCRIPTION "current number of open User sessions"
    ::= { userSessions 1}

-- 1.3.6.1.4.1.5678.2.1.3.10
userSessionsProcessed OBJECT-TYPE
    SYNTAX  Counter64
    MAX-ACCESS  read-only
    STATUS  current
    DESCRIPTION "total number of User sessions processed"
    ::= { userSessions 10}

-- 1.3.6.1.4.1.5678.2.1.3.12
userSessionsTimeouted OBJECT-TYPE
    SYNTAX  Counter64
    MAX-ACCESS  read-only
    STATUS  current
    DESCRIPTION "total number of timed out User sessions"
    ::= { userSessions 12}

-- 1.3.6.1.4.1.5678.2.1.3.26
userMessagesComposed OBJECT-TYPE
    SYNTAX  Counter64
    MAX-ACCESS  read-only
    STATUS  current
    DESCRIPTION "total number of User messages composed"
    ::= { userSessions 26}

-- 1.3.6.1.4.1.5678.2.1.3.30
userRequestsProcessed OBJECT-TYPE
    SYNTAX  Counter64
    MAX-ACCESS  read-only
    STATUS  current
    DESCRIPTION "total number of User requests processed"
    ::= { userSessions 30}

-- 1.3.6.1.4.1.5678.2.1.4
cGateProSecurity OBJECT IDENTIFIER
    ::= { cGateProObject 4}

-- 1.3.6.1.4.1.5678.2.1.4.1
numInactiveTLSSessions OBJECT-TYPE
    SYNTAX  Integer32
    MAX-ACCESS  read-only
    STATUS  current
    DESCRIPTION "current number of inactive (cached) TLS sessions"
    ::= { cGateProSecurity 1}

-- 1.3.6.1.4.1.5678.2.1.4.2
numActiveTLSSessions OBJECT-TYPE
    SYNTAX  Integer32
    MAX-ACCESS  read-only
    STATUS  current
    DESCRIPTION "current number of active TLS sessions"
    ::= { cGateProSecurity 2}

-- 1.3.6.1.4.1.5678.2.1.4.3
numActiveTLSConnections OBJECT-TYPE
    SYNTAX  Integer32
    MAX-ACCESS  read-only
    STATUS  current
    DESCRIPTION "current number of active TLS connections"
    ::= { cGateProSecurity 3}

-- 1.3.6.1.4.1.5678.2.1.4.10
processedTLSSessions OBJECT-TYPE
    SYNTAX  Counter64
    MAX-ACCESS  read-only
    STATUS  current
    DESCRIPTION "total number of processed TLS sessions"
    ::= { cGateProSecurity 10}

-- 1.3.6.1.4.1.5678.2.1.5
cCGateProAUTH OBJECT IDENTIFIER
    ::= { cGateProObject 5}

-- 1.3.6.1.4.1.5678.2.1.5.1
successfulAUTHs OBJECT-TYPE
    SYNTAX  Counter64
    MAX-ACCESS  read-only
    STATUS  current
    DESCRIPTION "total number of successful authentications"
    ::= { cCGateProAUTH 1}

-- 1.3.6.1.4.1.5678.2.1.5.2
failedAUTHs OBJECT-TYPE
    SYNTAX  Counter64
    MAX-ACCESS  read-only
    STATUS  current
    DESCRIPTION "total number of failed authentications"
    ::= { cCGateProAUTH 2}

-- 1.3.6.1.4.1.5678.2.1.5.3
secureAUTHs OBJECT-TYPE
    SYNTAX  Counter64
    MAX-ACCESS  read-only
    STATUS  current
    DESCRIPTION "total number of secure authentications"
    ::= { cCGateProAUTH 3}

-- 1.3.6.1.4.1.5678.2.1.5.10
osBasedAUTHs OBJECT-TYPE
    SYNTAX  Counter64
    MAX-ACCESS  read-only
    STATUS  current
    DESCRIPTION "total number of OS-based authentications"
    ::= { cCGateProAUTH 10}

-- 1.3.6.1.4.1.5678.2.1.5.11
externalAUTHs OBJECT-TYPE
    SYNTAX  Counter64
    MAX-ACCESS  read-only
    STATUS  current
    DESCRIPTION "total number of external authentications"
    ::= { cCGateProAUTH 11}

-- 1.3.6.1.4.1.5678.2.1.5.12
extLDAPAUTHs OBJECT-TYPE
    SYNTAX  Counter64
    MAX-ACCESS  read-only
    STATUS  current
    DESCRIPTION "total number of external authentications via LDAP URI"
    ::= { cCGateProAUTH 12}

-- 1.3.6.1.4.1.5678.2.1.5.13
adminAUTHs OBJECT-TYPE
    SYNTAX  Counter64
    MAX-ACCESS  read-only
    STATUS  current
    DESCRIPTION "total number of authentications for admin accounts from new IPs"
    ::= { cCGateProAUTH 13}

-- 1.3.6.1.4.1.5678.2.1.5.15
rejectedOnFailureAUTHs OBJECT-TYPE
    SYNTAX  Counter64
    MAX-ACCESS  read-only
    STATUS  current
    DESCRIPTION "total number of authentication requests rejected due to failure rate"
    ::= { cCGateProAUTH 15}

-- 1.3.6.1.4.1.5678.2.1.5.16
rejectedOnMethodAUTHs OBJECT-TYPE
    SYNTAX  Counter64
    MAX-ACCESS  read-only
    STATUS  current
    DESCRIPTION "total number of authentication requests rejected due to non-secure methods used"
    ::= { cCGateProAUTH 16}

-- 1.3.6.1.4.1.5678.2.1.7
cGateProProxy OBJECT IDENTIFIER
    ::= { cGateProObject 7}

-- 1.3.6.1.4.1.5678.2.1.7.1
proxyActive OBJECT-TYPE
    SYNTAX  Integer32
    MAX-ACCESS  read-only
    STATUS  current
    DESCRIPTION "number of active media proxies"
    ::= { cGateProProxy 1}

-- 1.3.6.1.4.1.5678.2.1.7.2
proxyTotalUdp OBJECT-TYPE
    SYNTAX  Counter64
    MAX-ACCESS  read-only
    STATUS  current
    DESCRIPTION "total number of UDP proxies created"
    ::= { cGateProProxy 2}

-- 1.3.6.1.4.1.5678.2.1.7.5
proxyTotalTcp OBJECT-TYPE
    SYNTAX  Counter64
    MAX-ACCESS  read-only
    STATUS  current
    DESCRIPTION "total number of TCP proxies created"
    ::= { cGateProProxy 5}

-- 1.3.6.1.4.1.5678.2.1.7.6
proxyTotalTcpConnects OBJECT-TYPE
    SYNTAX  Counter64
    MAX-ACCESS  read-only
    STATUS  current
    DESCRIPTION "total number of TCP connections attempted"
    ::= { cGateProProxy 6}

-- 1.3.6.1.4.1.5678.2.1.7.11
proxySentToLANudpBytes OBJECT-TYPE
    SYNTAX  Counter64
    MAX-ACCESS  read-only
    STATUS  current
    DESCRIPTION "udp bytes sent to LAN"
    ::= { cGateProProxy 11}

-- 1.3.6.1.4.1.5678.2.1.7.12
proxySentToWANudpBytes OBJECT-TYPE
    SYNTAX  Counter64
    MAX-ACCESS  read-only
    STATUS  current
    DESCRIPTION "udp bytes sent to WAN"
    ::= { cGateProProxy 12}

-- 1.3.6.1.4.1.5678.2.1.7.13
proxySentToNATudpBytes OBJECT-TYPE
    SYNTAX  Counter64
    MAX-ACCESS  read-only
    STATUS  current
    DESCRIPTION "udp bytes sent to NATed"
    ::= { cGateProProxy 13}

-- 1.3.6.1.4.1.5678.2.1.7.16
proxySentToLANudpPackets OBJECT-TYPE
    SYNTAX  Counter64
    MAX-ACCESS  read-only
    STATUS  current
    DESCRIPTION "udp packets sent to LAN"
    ::= { cGateProProxy 16}

-- 1.3.6.1.4.1.5678.2.1.7.17
proxySentToWANudpPackets OBJECT-TYPE
    SYNTAX  Counter64
    MAX-ACCESS  read-only
    STATUS  current
    DESCRIPTION "udp packets sent to WAN"
    ::= { cGateProProxy 17}

-- 1.3.6.1.4.1.5678.2.1.7.18
proxySentToNATudpPackets OBJECT-TYPE
    SYNTAX  Counter64
    MAX-ACCESS  read-only
    STATUS  current
    DESCRIPTION "udp packets sent to NATed"
    ::= { cGateProProxy 18}

-- 1.3.6.1.4.1.5678.2.1.7.20
proxySentToLANtcpBytes OBJECT-TYPE
    SYNTAX  Counter64
    MAX-ACCESS  read-only
    STATUS  current
    DESCRIPTION "tcp bytes sent to LAN"
    ::= { cGateProProxy 20}

-- 1.3.6.1.4.1.5678.2.1.7.21
proxySentToWANtcpBytes OBJECT-TYPE
    SYNTAX  Counter64
    MAX-ACCESS  read-only
    STATUS  current
    DESCRIPTION "tcp bytes sent to WAN"
    ::= { cGateProProxy 21}

-- 1.3.6.1.4.1.5678.2.1.7.22
proxySentToNATtcpBytes OBJECT-TYPE
    SYNTAX  Counter64
    MAX-ACCESS  read-only
    STATUS  current
    DESCRIPTION "tcp bytes sent to NAT"
    ::= { cGateProProxy 22}

-- 1.3.6.1.4.1.5678.2.1.7.25
proxyAcceptsFromLAN OBJECT-TYPE
    SYNTAX  Counter64
    MAX-ACCESS  read-only
    STATUS  current
    DESCRIPTION "tcp connections from LAN"
    ::= { cGateProProxy 25}

-- 1.3.6.1.4.1.5678.2.1.7.26
proxyAcceptsFromWAN OBJECT-TYPE
    SYNTAX  Counter64
    MAX-ACCESS  read-only
    STATUS  current
    DESCRIPTION "tcp connections from WAN"
    ::= { cGateProProxy 26}

-- 1.3.6.1.4.1.5678.2.1.7.27
proxyAcceptsFromNAT OBJECT-TYPE
    SYNTAX  Counter64
    MAX-ACCESS  read-only
    STATUS  current
    DESCRIPTION "tcp connections from NAT"
    ::= { cGateProProxy 27}

-- 1.3.6.1.4.1.5678.2.1.9
cGateProSignal OBJECT IDENTIFIER
    ::= { cGateProObject 9}

-- 1.3.6.1.4.1.5678.2.1.9.1
signalActive OBJECT-TYPE
    SYNTAX  Integer32
    MAX-ACCESS  read-only
    STATUS  current
    DESCRIPTION "active real-time signals"
    ::= { cGateProSignal 1}

-- 1.3.6.1.4.1.5678.2.1.9.2
signalTotal OBJECT-TYPE
    SYNTAX  Counter64
    MAX-ACCESS  read-only
    STATUS  current
    DESCRIPTION "total real-time signals processed"
    ::= { cGateProSignal 2}

-- 1.3.6.1.4.1.5678.2.1.9.3
signalActiveEvents OBJECT-TYPE
    SYNTAX  Integer32
    MAX-ACCESS  read-only
    STATUS  current
    DESCRIPTION "unprocessed real-time signal events"
    ::= { cGateProSignal 3}

-- 1.3.6.1.4.1.5678.2.1.9.4
signalTotalEvents OBJECT-TYPE
    SYNTAX  Counter64
    MAX-ACCESS  read-only
    STATUS  current
    DESCRIPTION "total real-time signal events processed"
    ::= { cGateProSignal 4}

-- 1.3.6.1.4.1.5678.2.1.9.5
signalBusyThreads OBJECT-TYPE
    SYNTAX  Integer32
    MAX-ACCESS  read-only
    STATUS  current
    DESCRIPTION "busy real-time signal processors"
    ::= { cGateProSignal 5}

-- 1.3.6.1.4.1.5678.2.1.9.6
signalOverloads OBJECT-TYPE
    SYNTAX  Counter64
    MAX-ACCESS  read-only
    STATUS  current
    DESCRIPTION "total real-time signal subsystem overloads"
    ::= { cGateProSignal 6}

-- 1.3.6.1.4.1.5678.2.1.10
cGateProNATPing OBJECT IDENTIFIER
    ::= { cGateProObject 10}

-- 1.3.6.1.4.1.5678.2.1.10.1
natPingersActive OBJECT-TYPE
    SYNTAX  Integer32
    MAX-ACCESS  read-only
    STATUS  current
    DESCRIPTION "active NAT pingers"
    ::= { cGateProNATPing 1}

-- 1.3.6.1.4.1.5678.2.1.10.2
natPingersTotal OBJECT-TYPE
    SYNTAX  Counter64
    MAX-ACCESS  read-only
    STATUS  current
    DESCRIPTION "total number of NAT pingers created"
    ::= { cGateProNATPing 2}

-- 1.3.6.1.4.1.5678.2.1.10.3
natPingersUpdated OBJECT-TYPE
    SYNTAX  Counter64
    MAX-ACCESS  read-only
    STATUS  current
    DESCRIPTION "total number of NAT pingers udpated"
    ::= { cGateProNATPing 3}

-- 1.3.6.1.4.1.5678.2.1.10.4
natPingersErrors OBJECT-TYPE
    SYNTAX  Counter64
    MAX-ACCESS  read-only
    STATUS  current
    DESCRIPTION "total number of NAT pinger errors"
    ::= { cGateProNATPing 4}

-- 1.3.6.1.4.1.5678.2.1.11
cGateProRTNode OBJECT IDENTIFIER
    ::= { cGateProObject 11}

-- 1.3.6.1.4.1.5678.2.1.11.1
realTimeNodeActive OBJECT-TYPE
    SYNTAX  Integer32
    MAX-ACCESS  read-only
    STATUS  current
    DESCRIPTION "active real-time nodes"
    ::= { cGateProRTNode 1}

-- 1.3.6.1.4.1.5678.2.1.11.2
realTimeNodeTotal OBJECT-TYPE
    SYNTAX  Counter64
    MAX-ACCESS  read-only
    STATUS  current
    DESCRIPTION "total real-time nodes created"
    ::= { cGateProRTNode 2}

-- 1.3.6.1.4.1.5678.2.1.11.3
realTimeNodeActiveEvents OBJECT-TYPE
    SYNTAX  Integer32
    MAX-ACCESS  read-only
    STATUS  current
    DESCRIPTION "unprocessed real-time node events"
    ::= { cGateProRTNode 3}

-- 1.3.6.1.4.1.5678.2.1.11.4
realTimeNodeTotalEvents OBJECT-TYPE
    SYNTAX  Counter64
    MAX-ACCESS  read-only
    STATUS  current
    DESCRIPTION "total real-time node events processed"
    ::= { cGateProRTNode 4}

-- 1.3.6.1.4.1.5678.2.1.11.5
realTimeNodeBusyThreads OBJECT-TYPE
    SYNTAX  Integer32
    MAX-ACCESS  read-only
    STATUS  current
    DESCRIPTION "busy real-time node processors"
    ::= { cGateProRTNode 5}

-- 1.3.6.1.4.1.5678.2.1.11.6
realTimeNodeOverloads OBJECT-TYPE
    SYNTAX  Counter64
    MAX-ACCESS  read-only
    STATUS  current
    DESCRIPTION "total real-time node subsystem overloads"
    ::= { cGateProRTNode 6}

-- 1.3.6.1.4.1.5678.2.1.12
cGateProTempFiles OBJECT IDENTIFIER
    ::= { cGateProObject 12}

-- 1.3.6.1.4.1.5678.2.1.12.1
totalCreatedTempFiles OBJECT-TYPE
    SYNTAX  Counter64
    MAX-ACCESS  read-only
    STATUS  current
    DESCRIPTION "total number of created temp files"
    ::= { cGateProTempFiles 1}

-- 1.3.6.1.4.1.5678.2.1.12.2
availableTempFiles OBJECT-TYPE
    SYNTAX  Integer32
    MAX-ACCESS  read-only
    STATUS  current
    DESCRIPTION "currently available temp files"
    ::= { cGateProTempFiles 2}

-- 1.3.6.1.4.1.5678.2.1.12.3
totalReusedTempFiles OBJECT-TYPE
    SYNTAX  Counter64
    MAX-ACCESS  read-only
    STATUS  current
    DESCRIPTION "total number of recycled temp files"
    ::= { cGateProTempFiles 3}

-- 1.3.6.1.4.1.5678.2.1.12.4
totalDeletedTempFiles OBJECT-TYPE
    SYNTAX  Counter64
    MAX-ACCESS  read-only
    STATUS  current
    DESCRIPTION "total number of deleted temp files"
    ::= { cGateProTempFiles 4}

-- 1.3.6.1.4.1.5678.2.1.13
cGateProMainLog OBJECT IDENTIFIER
    ::= { cGateProObject 13}

-- 1.3.6.1.4.1.5678.2.1.13.1
totalLogLines OBJECT-TYPE
    SYNTAX  Counter64
    MAX-ACCESS  read-only
    STATUS  current
    DESCRIPTION "total number of recorded Log records"
    ::= { cGateProMainLog 1}

-- 1.3.6.1.4.1.5678.2.1.13.2
totalLogBytes OBJECT-TYPE
    SYNTAX  Counter64
    MAX-ACCESS  read-only
    STATUS  current
    DESCRIPTION "total size of recorded Log records"
    ::= { cGateProMainLog 2}

-- 1.3.6.1.4.1.5678.2.1.13.3
totalLogOverflows OBJECT-TYPE
    SYNTAX  Counter64
    MAX-ACCESS  read-only
    STATUS  current
    DESCRIPTION "total number of Log buffer overflows"
    ::= { cGateProMainLog 3}

-- 1.3.6.1.4.1.5678.2.1.13.100
logLastCrashRecord OBJECT-TYPE
    SYNTAX  OCTET STRING
    MAX-ACCESS  read-only
    STATUS  current
    DESCRIPTION "latest Crash-level Log record"
    ::= { cGateProMainLog 100}

-- 1.3.6.1.4.1.5678.2.1.14
cGateProCall OBJECT IDENTIFIER
    ::= { cGateProObject 14}

-- 1.3.6.1.4.1.5678.2.1.14.1
callActive OBJECT-TYPE
    SYNTAX  Integer32
    MAX-ACCESS  read-only
    STATUS  current
    DESCRIPTION "current number of active calls"
    ::= { cGateProCall 1}

-- 1.3.6.1.4.1.5678.2.1.14.2
callTotal OBJECT-TYPE
    SYNTAX  Counter64
    MAX-ACCESS  read-only
    STATUS  current
    DESCRIPTION "total number of calls initiated"
    ::= { cGateProCall 2}

-- 1.3.6.1.4.1.5678.2.1.14.10
callCompleted OBJECT-TYPE
    SYNTAX  Counter64
    MAX-ACCESS  read-only
    STATUS  current
    DESCRIPTION "total number of completed calls"
    ::= { cGateProCall 10}

-- 1.3.6.1.4.1.5678.2.1.14.11
callFailed OBJECT-TYPE
    SYNTAX  Counter64
    MAX-ACCESS  read-only
    STATUS  current
    DESCRIPTION "total number of failed calls"
    ::= { cGateProCall 11}

-- 1.3.6.1.4.1.5678.2.1.14.12
callTime OBJECT-TYPE
    SYNTAX  Counter64
    MAX-ACCESS  read-only
    STATUS  current
    DESCRIPTION "total duration of completed calls (seconds)"
    ::= { cGateProCall 12}

-- 1.3.6.1.4.1.5678.2.1.15
cGateProMedia OBJECT IDENTIFIER
    ::= { cGateProObject 15}

-- 1.3.6.1.4.1.5678.2.1.15.1
mediaChannelsActive OBJECT-TYPE
    SYNTAX  Integer32
    MAX-ACCESS  read-only
    STATUS  current
    DESCRIPTION "number of active media channels"
    ::= { cGateProMedia 1}

-- 1.3.6.1.4.1.5678.2.1.15.2
mediaChannelsTotal OBJECT-TYPE
    SYNTAX  Counter64
    MAX-ACCESS  read-only
    STATUS  current
    DESCRIPTION "total number of media channels created"
    ::= { cGateProMedia 2}

-- 1.3.6.1.4.1.5678.2.1.15.21
mediaLegsActive OBJECT-TYPE
    SYNTAX  Integer32
    MAX-ACCESS  read-only
    STATUS  current
    DESCRIPTION "number of active media legs"
    ::= { cGateProMedia 21}

-- 1.3.6.1.4.1.5678.2.1.15.22
mediaLegsTotal OBJECT-TYPE
    SYNTAX  Counter64
    MAX-ACCESS  read-only
    STATUS  current
    DESCRIPTION "total number of media legs created"
    ::= { cGateProMedia 22}

-- 1.3.6.1.4.1.5678.2.1.15.31
mediaBytesReceived OBJECT-TYPE
    SYNTAX  Counter64
    MAX-ACCESS  read-only
    STATUS  current
    DESCRIPTION "total number of media bytes received"
    ::= { cGateProMedia 31}

-- 1.3.6.1.4.1.5678.2.1.15.32
mediaBytesSent OBJECT-TYPE
    SYNTAX  Counter64
    MAX-ACCESS  read-only
    STATUS  current
    DESCRIPTION "total number of media bytes sent"
    ::= { cGateProMedia 32}

-- 1.3.6.1.4.1.5678.2.1.15.33
mediaPacketsReceived OBJECT-TYPE
    SYNTAX  Counter64
    MAX-ACCESS  read-only
    STATUS  current
    DESCRIPTION "total number of media packets received"
    ::= { cGateProMedia 33}

-- 1.3.6.1.4.1.5678.2.1.15.34
mediaPacketsSent OBJECT-TYPE
    SYNTAX  Counter64
    MAX-ACCESS  read-only
    STATUS  current
    DESCRIPTION "total number of media packets sent"
    ::= { cGateProMedia 34}

-- 1.3.6.1.4.1.5678.2.1.15.35
mediaPacketsLost OBJECT-TYPE
    SYNTAX  Counter64
    MAX-ACCESS  read-only
    STATUS  current
    DESCRIPTION "total number of media packets lost"
    ::= { cGateProMedia 35}

-- 1.3.6.1.4.1.5678.2.1.15.36
mediaPacketsReordered OBJECT-TYPE
    SYNTAX  Counter64
    MAX-ACCESS  read-only
    STATUS  current
    DESCRIPTION "total number of media packets received reordered"
    ::= { cGateProMedia 36}

-- 1.3.6.1.4.1.5678.2.1.15.40
mediaDTMFReceived OBJECT-TYPE
    SYNTAX  Counter64
    MAX-ACCESS  read-only
    STATUS  current
    DESCRIPTION "total number of DTMF symbols received"
    ::= { cGateProMedia 40}

-- 1.3.6.1.4.1.5678.2.1.15.41
mediaDTMFSent OBJECT-TYPE
    SYNTAX  Counter64
    MAX-ACCESS  read-only
    STATUS  current
    DESCRIPTION "total number of DTMF symbols sent"
    ::= { cGateProMedia 41}

-- 1.3.6.1.4.1.5678.2.1.16
cGateProNetwork OBJECT IDENTIFIER
    ::= { cGateProObject 16}

-- 1.3.6.1.4.1.5678.2.1.16.1
dnr OBJECT IDENTIFIER
    ::= { cGateProNetwork 1}

-- 1.3.6.1.4.1.5678.2.1.16.1.1
dnrUDPRequestsTotal OBJECT-TYPE
    SYNTAX  Counter64
    MAX-ACCESS  read-only
    STATUS  current
    DESCRIPTION "total number of DNR UDP requests sent"
    ::= { dnr 1}

-- 1.3.6.1.4.1.5678.2.1.16.1.2
dnrUDPRequestsPending OBJECT-TYPE
    SYNTAX  Integer32
    MAX-ACCESS  read-only
    STATUS  current
    DESCRIPTION "pending DNR UDP requests"
    ::= { dnr 2}

-- 1.3.6.1.4.1.5678.2.1.16.1.3
dnrUDPTimeouts OBJECT-TYPE
    SYNTAX  Counter64
    MAX-ACCESS  read-only
    STATUS  current
    DESCRIPTION "total number of timed out DNR UDP requests"
    ::= { dnr 3}

-- 1.3.6.1.4.1.5678.2.1.16.1.4
dnrUDPSendErrors OBJECT-TYPE
    SYNTAX  Counter64
    MAX-ACCESS  read-only
    STATUS  current
    DESCRIPTION "total number of timed out DNR UDP send errors"
    ::= { dnr 4}

-- 1.3.6.1.4.1.5678.2.1.16.1.10
dnrTotalTCPRequests OBJECT-TYPE
    SYNTAX  Counter64
    MAX-ACCESS  read-only
    STATUS  current
    DESCRIPTION "total number of DNR TCP requests sent"
    ::= { dnr 10}

-- 1.3.6.1.4.1.5678.2.1.16.10
ports OBJECT IDENTIFIER
    ::= { cGateProNetwork 10}

-- 1.3.6.1.4.1.5678.2.1.16.10.10
tcpPortAllocationFailures OBJECT-TYPE
    SYNTAX  Counter64
    MAX-ACCESS  read-only
    STATUS  current
    DESCRIPTION "total failed attempts to allocate a TCP port"
    ::= { ports 10}

-- 1.3.6.1.4.1.5678.2.1.16.10.12
udpPortAllocationFailures OBJECT-TYPE
    SYNTAX  Counter64
    MAX-ACCESS  read-only
    STATUS  current
    DESCRIPTION "total failed attempts to allocate a UDP port"
    ::= { ports 12}

-- 1.3.6.1.4.1.5678.2.1.30
cGateProMailbox OBJECT IDENTIFIER
    ::= { cGateProObject 30}

-- 1.3.6.1.4.1.5678.2.1.30.1
numOpenRealMailboxes OBJECT-TYPE
    SYNTAX  Integer32
    MAX-ACCESS  read-only
    STATUS  current
    DESCRIPTION "current number of open real mailboxes"
    ::= { cGateProMailbox 1}

-- 1.3.6.1.4.1.5678.2.1.30.2
totalOpenRealMailboxes OBJECT-TYPE
    SYNTAX  Counter64
    MAX-ACCESS  read-only
    STATUS  current
    DESCRIPTION "total number of real mailboxes open"
    ::= { cGateProMailbox 2}

-- 1.3.6.1.4.1.5678.2.1.30.3
numOpenVirtMailboxes OBJECT-TYPE
    SYNTAX  Integer32
    MAX-ACCESS  read-only
    STATUS  current
    DESCRIPTION "current number of open virtual mailboxes"
    ::= { cGateProMailbox 3}

-- 1.3.6.1.4.1.5678.2.1.30.4
totalOpenVirtMailboxes OBJECT-TYPE
    SYNTAX  Counter64
    MAX-ACCESS  read-only
    STATUS  current
    DESCRIPTION "total number of virtual mailboxes open"
    ::= { cGateProMailbox 4}

-- 1.3.6.1.4.1.5678.2.1.30.20
numTextIndexReading OBJECT-TYPE
    SYNTAX  Integer32
    MAX-ACCESS  read-only
    STATUS  current
    DESCRIPTION "current number of processors reading text mailbox indices"
    ::= { cGateProMailbox 20}

-- 1.3.6.1.4.1.5678.2.1.30.21
totalTextIndexRead OBJECT-TYPE
    SYNTAX  Counter64
    MAX-ACCESS  read-only
    STATUS  current
    DESCRIPTION "total number of text mailbox indices read"
    ::= { cGateProMailbox 21}

-- 1.3.6.1.4.1.5678.2.1.30.22
totalTextIndexBytesRead OBJECT-TYPE
    SYNTAX  Counter64
    MAX-ACCESS  read-only
    STATUS  current
    DESCRIPTION "total size of text mailbox indices read"
    ::= { cGateProMailbox 22}

-- 1.3.6.1.4.1.5678.2.1.30.25
numTextIndexWriting OBJECT-TYPE
    SYNTAX  Integer32
    MAX-ACCESS  read-only
    STATUS  current
    DESCRIPTION "current number of processors writing text mailbox indices"
    ::= { cGateProMailbox 25}

-- 1.3.6.1.4.1.5678.2.1.30.26
totalTextIndexWritten OBJECT-TYPE
    SYNTAX  Counter64
    MAX-ACCESS  read-only
    STATUS  current
    DESCRIPTION "total number of text mailbox indices written"
    ::= { cGateProMailbox 26}

-- 1.3.6.1.4.1.5678.2.1.30.27
totalTextIndexBytesWritten OBJECT-TYPE
    SYNTAX  Counter64
    MAX-ACCESS  read-only
    STATUS  current
    DESCRIPTION "total size of text mailbox indices written"
    ::= { cGateProMailbox 27}

-- 1.3.6.1.4.1.5678.2.1.30.30
numTextParsing OBJECT-TYPE
    SYNTAX  Integer32
    MAX-ACCESS  read-only
    STATUS  current
    DESCRIPTION "current number of processors parsing text mailboxes"
    ::= { cGateProMailbox 30}

-- 1.3.6.1.4.1.5678.2.1.30.31
totalTextParsed OBJECT-TYPE
    SYNTAX  Counter64
    MAX-ACCESS  read-only
    STATUS  current
    DESCRIPTION "total number of text mailboxes parsed"
    ::= { cGateProMailbox 31}

-- 1.3.6.1.4.1.5678.2.1.30.32
totalTextParseBytesRead OBJECT-TYPE
    SYNTAX  Counter64
    MAX-ACCESS  read-only
    STATUS  current
    DESCRIPTION "total size of text mailboxes parsed"
    ::= { cGateProMailbox 32}

-- 1.3.6.1.4.1.5678.2.1.30.35
numTextUpdating OBJECT-TYPE
    SYNTAX  Integer32
    MAX-ACCESS  read-only
    STATUS  current
    DESCRIPTION "current number of processors updating text mailboxes"
    ::= { cGateProMailbox 35}

-- 1.3.6.1.4.1.5678.2.1.30.36
totalTextCleaned OBJECT-TYPE
    SYNTAX  Counter64
    MAX-ACCESS  read-only
    STATUS  current
    DESCRIPTION "total number of text mailboxes updated"
    ::= { cGateProMailbox 36}

-- 1.3.6.1.4.1.5678.2.1.30.37
totalTextCleanBytesWritten OBJECT-TYPE
    SYNTAX  Counter64
    MAX-ACCESS  read-only
    STATUS  current
    DESCRIPTION "total size of text mailboxes updates"
    ::= { cGateProMailbox 37}

-- 1.3.6.1.4.1.5678.2.1.30.50
numLargeTextBuffers OBJECT-TYPE
    SYNTAX  Integer32
    MAX-ACCESS  read-only
    STATUS  current
    DESCRIPTION "current number of large text mailboxes buffers allocated"
    ::= { cGateProMailbox 50}

-- 1.3.6.1.4.1.5678.2.1.31
cGateProAccount OBJECT IDENTIFIER
    ::= { cGateProObject 31}

-- 1.3.6.1.4.1.5678.2.1.31.1
numOpenAccounts OBJECT-TYPE
    SYNTAX  Integer32
    MAX-ACCESS  read-only
    STATUS  current
    DESCRIPTION "current number of open accounts"
    ::= { cGateProAccount 1}

-- 1.3.6.1.4.1.5678.2.1.31.2
totalOpenAccounts OBJECT-TYPE
    SYNTAX  Counter64
    MAX-ACCESS  read-only
    STATUS  current
    DESCRIPTION "total number of accounts open"
    ::= { cGateProAccount 2}

-- 1.3.6.1.4.1.5678.2.1.31.3
totalReopenAccounts OBJECT-TYPE
    SYNTAX  Counter64
    MAX-ACCESS  read-only
    STATUS  current
    DESCRIPTION "total number of accounts re-open"
    ::= { cGateProAccount 3}

-- 1.3.6.1.4.1.5678.2.1.31.4
totalCacheOpenedAccounts OBJECT-TYPE
    SYNTAX  Counter64
    MAX-ACCESS  read-only
    STATUS  current
    DESCRIPTION "total number of accounts open from cache"
    ::= { cGateProAccount 4}

-- 1.3.6.1.4.1.5678.2.1.31.5
numCachedAccounts OBJECT-TYPE
    SYNTAX  Integer32
    MAX-ACCESS  read-only
    STATUS  current
    DESCRIPTION "current number of cached accounts"
    ::= { cGateProAccount 5}

-- 1.3.6.1.4.1.5678.2.1.31.6
totalOpenedTempAccounts OBJECT-TYPE
    SYNTAX  Counter64
    MAX-ACCESS  read-only
    STATUS  current
    DESCRIPTION "total number of temp accounts open"
    ::= { cGateProAccount 6}

-- 1.3.6.1.4.1.5678.2.1.1000
cGateProCustom OBJECT IDENTIFIER
    ::= { cGateProObject 1000}

-- 1.3.6.1.4.1.5678.2.1.1000.1
custom1 OBJECT-TYPE
    SYNTAX  Counter64
    MAX-ACCESS  read-only
    STATUS  current
    DESCRIPTION "custom counter 1"
    ::= { cGateProCustom 1}

-- 1.3.6.1.4.1.5678.2.1.1000.2
custom2 OBJECT-TYPE
    SYNTAX  Counter64
    MAX-ACCESS  read-only
    STATUS  current
    DESCRIPTION "custom counter 2"
    ::= { cGateProCustom 2}

-- 1.3.6.1.4.1.5678.2.1.1000.3
custom3 OBJECT-TYPE
    SYNTAX  Counter64
    MAX-ACCESS  read-only
    STATUS  current
    DESCRIPTION "custom counter 3"
    ::= { cGateProCustom 3}

-- 1.3.6.1.4.1.5678.2.1.1000.4
custom4 OBJECT-TYPE
    SYNTAX  Counter64
    MAX-ACCESS  read-only
    STATUS  current
    DESCRIPTION "custom counter 4"
    ::= { cGateProCustom 4}

-- 1.3.6.1.4.1.5678.2.1.1000.5
custom5 OBJECT-TYPE
    SYNTAX  Counter64
    MAX-ACCESS  read-only
    STATUS  current
    DESCRIPTION "custom counter 5"
    ::= { cGateProCustom 5}

-- 1.3.6.1.4.1.5678.2.1.1000.6
custom6 OBJECT-TYPE
    SYNTAX  Counter64
    MAX-ACCESS  read-only
    STATUS  current
    DESCRIPTION "custom counter 6"
    ::= { cGateProCustom 6}

-- 1.3.6.1.4.1.5678.2.1.1000.7
custom7 OBJECT-TYPE
    SYNTAX  Counter64
    MAX-ACCESS  read-only
    STATUS  current
    DESCRIPTION "custom counter 7"
    ::= { cGateProCustom 7}

-- 1.3.6.1.4.1.5678.2.1.1000.8
custom8 OBJECT-TYPE
    SYNTAX  Counter64
    MAX-ACCESS  read-only
    STATUS  current
    DESCRIPTION "custom counter 8"
    ::= { cGateProCustom 8}

-- 1.3.6.1.4.1.5678.2.1.1000.9
custom9 OBJECT-TYPE
    SYNTAX  Counter64
    MAX-ACCESS  read-only
    STATUS  current
    DESCRIPTION "custom counter 9"
    ::= { cGateProCustom 9}

-- 1.3.6.1.4.1.5678.2.1.1000.10
custom10 OBJECT-TYPE
    SYNTAX  Counter64
    MAX-ACCESS  read-only
    STATUS  current
    DESCRIPTION "custom counter 10"
    ::= { cGateProCustom 10}

-- 1.3.6.1.4.1.5678.2.100
foundation OBJECT IDENTIFIER
    ::= { communiGatePro 100}

-- 1.3.6.1.4.1.5678.2.100.1
activeObjects OBJECT-TYPE
    SYNTAX  Integer32
    MAX-ACCESS  read-only
    STATUS  current
    DESCRIPTION "number of active objects"
    ::= { foundation 1}

-- 1.3.6.1.4.1.5678.2.100.2
totalObjects OBJECT-TYPE
    SYNTAX  Counter64
    MAX-ACCESS  read-only
    STATUS  current
    DESCRIPTION "total number of created objects"
    ::= { foundation 2}

-- 1.3.6.1.4.1.5678.2.100.20
activeThreads OBJECT-TYPE
    SYNTAX  Integer32
    MAX-ACCESS  read-only
    STATUS  current
    DESCRIPTION "number of active threads"
    ::= { foundation 20}

-- 1.3.6.1.4.1.5678.2.100.21
totalThreads OBJECT-TYPE
    SYNTAX  Counter64
    MAX-ACCESS  read-only
    STATUS  current
    DESCRIPTION "total number of created threads"
    ::= { foundation 21}

-- 1.3.6.1.4.1.5678.2.100.40
tcpBytesSent OBJECT-TYPE
    SYNTAX  Counter64
    MAX-ACCESS  read-only
    STATUS  current
    DESCRIPTION "total TCP data sent"
    ::= { foundation 40}

-- 1.3.6.1.4.1.5678.2.100.41
tcpBytesRead OBJECT-TYPE
    SYNTAX  Counter64
    MAX-ACCESS  read-only
    STATUS  current
    DESCRIPTION "total TCP data read"
    ::= { foundation 41}

-- 1.3.6.1.4.1.5678.2.100.42
tcpOutStarted OBJECT-TYPE
    SYNTAX  Counter64
    MAX-ACCESS  read-only
    STATUS  current
    DESCRIPTION "total TCP connections started"
    ::= { foundation 42}

-- 1.3.6.1.4.1.5678.2.100.43
tcpAccepted OBJECT-TYPE
    SYNTAX  Counter64
    MAX-ACCESS  read-only
    STATUS  current
    DESCRIPTION "total TCP connections accepted"
    ::= { foundation 43}

-- 1.3.6.1.4.1.5678.2.100.50
udpBytesSent OBJECT-TYPE
    SYNTAX  Counter64
    MAX-ACCESS  read-only
    STATUS  current
    DESCRIPTION "total UDP data sent"
    ::= { foundation 50}

-- 1.3.6.1.4.1.5678.2.100.51
udpBytesRead OBJECT-TYPE
    SYNTAX  Counter64
    MAX-ACCESS  read-only
    STATUS  current
    DESCRIPTION "total UDP data read"
    ::= { foundation 51}

-- 1.3.6.1.4.1.5678.2.100.52
udpPacketsSent OBJECT-TYPE
    SYNTAX  Counter64
    MAX-ACCESS  read-only
    STATUS  current
    DESCRIPTION "total UDP packets sent"
    ::= { foundation 52}

-- 1.3.6.1.4.1.5678.2.100.53
udpPacketsRead OBJECT-TYPE
    SYNTAX  Counter64
    MAX-ACCESS  read-only
    STATUS  current
    DESCRIPTION "total UDP packets read"
    ::= { foundation 53}

-- 1.3.6.1.4.1.5678.2.100.100
fileOpens OBJECT-TYPE
    SYNTAX  Counter64
    MAX-ACCESS  read-only
    STATUS  current
    DESCRIPTION "total file open operations"
    ::= { foundation 100}

-- 1.3.6.1.4.1.5678.2.100.101
fileCloses OBJECT-TYPE
    SYNTAX  Counter64
    MAX-ACCESS  read-only
    STATUS  current
    DESCRIPTION "total file close operations"
    ::= { foundation 101}

-- 1.3.6.1.4.1.5678.2.100.102
fileBytesRead OBJECT-TYPE
    SYNTAX  Counter64
    MAX-ACCESS  read-only
    STATUS  current
    DESCRIPTION "total file bytes read"
    ::= { foundation 102}

-- 1.3.6.1.4.1.5678.2.100.103
fileBytesWritten OBJECT-TYPE
    SYNTAX  Counter64
    MAX-ACCESS  read-only
    STATUS  current
    DESCRIPTION "total file bytes written"
    ::= { foundation 103}

-- 1.3.6.1.4.1.5678.2.100.104
fileReads OBJECT-TYPE
    SYNTAX  Counter64
    MAX-ACCESS  read-only
    STATUS  current
    DESCRIPTION "total file read operations"
    ::= { foundation 104}

-- 1.3.6.1.4.1.5678.2.100.105
fileWrites OBJECT-TYPE
    SYNTAX  Counter64
    MAX-ACCESS  read-only
    STATUS  current
    DESCRIPTION "total file write operations"
    ::= { foundation 105}

-- 1.3.6.1.4.1.5678.2.100.106
fileSizeGets OBJECT-TYPE
    SYNTAX  Counter64
    MAX-ACCESS  read-only
    STATUS  current
    DESCRIPTION "total file size get operations"
    ::= { foundation 106}

-- 1.3.6.1.4.1.5678.2.100.107
fileSizeSets OBJECT-TYPE
    SYNTAX  Counter64
    MAX-ACCESS  read-only
    STATUS  current
    DESCRIPTION "total file size set operations"
    ::= { foundation 107}

-- 1.3.6.1.4.1.5678.2.100.108
fileSyncs OBJECT-TYPE
    SYNTAX  Counter64
    MAX-ACCESS  read-only
    STATUS  current
    DESCRIPTION "total file flush operations"
    ::= { foundation 108}

-- 1.3.6.1.4.1.5678.2.100.110
fileBytesRewritten OBJECT-TYPE
    SYNTAX  Counter64
    MAX-ACCESS  read-only
    STATUS  current
    DESCRIPTION "total file bytes re-written"
    ::= { foundation 110}

-- 1.3.6.1.4.1.5678.2.100.111
fileAtomicRewrites OBJECT-TYPE
    SYNTAX  Counter64
    MAX-ACCESS  read-only
    STATUS  current
    DESCRIPTION "total atomic file re-writes"
    ::= { foundation 111}

-- 1.3.6.1.4.1.5678.2.100.112
fileRegularRewrites OBJECT-TYPE
    SYNTAX  Counter64
    MAX-ACCESS  read-only
    STATUS  current
    DESCRIPTION "total regular file re-writes"
    ::= { foundation 112}

-- 1.3.6.1.4.1.5678.2.100.113
cpuTimeUsed OBJECT-TYPE
    SYNTAX  Counter64
    MAX-ACCESS  read-only
    STATUS  current
    DESCRIPTION "CPU time used by the process, in milliseconds"
    ::= { foundation 113}
END
